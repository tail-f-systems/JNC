module execd {
  namespace "http://tail-f.com/ns/execd/1.1";
  prefix execd;

  include execd-types;
  include execd-interfaces;
  include execd-syslog;
  include execd-dns;
  include execd-ntp;
  include execd-routes;

  organization "tail-f";
  description
    "The ExecD daemon manages a set of objects (e.g.  network interfaces)
     for a *NIX OS, based on a data model described in a set of YANG
     modules.

     The current version of ExecD includes these components:

       interfaces - configuration and status of network interfaces
       routes     - configuration of static routes
       syslog     - configuration of logging to remote syslog servers
       dns        - configuration of the DNS resolver
       ntp        - configuration and status of the NTP daemon

     This module is the main YANG module, and each component has its
     own YANG submodule.";

  revision 2008-11-04 {
    description
      "draft-ietf-netmod-yang-02 compatible.";
  }
  revision 2007-08-29 {
    description
      "Syntax fixes after pyang validation.";
  }
  revision 2007-06-08 {
    description
      "Initial revision.";
  }

  container sys {
    list temp {
      key a;
      leaf a {
        type instance-identifier;
      }
      leaf b {
        type empty;
      }
    }
    container interfaces {
      uses interfaces;
    }
    container routes {
      uses routes;
    }
    container syslog {
      uses syslog;
    }
    container ntp {
      uses ntp;
    }
    container dns {
      uses dns;
    }
  }
}
