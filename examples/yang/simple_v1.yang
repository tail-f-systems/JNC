module simple {
  namespace "http://acme.example.com/simple";
  prefix "simple";
    
  revision 2007-06-09 {
    description "Initial revision";
  }

  typedef mode-type {
    type enumeration {
      enum on;
      enum off;
    }
  }
    
  container config {
    leaf mode {
      type mode-type;
    }

    leaf host-metrics {
      type uint32 {
        range 0..64;
      }
    }
  }
}
