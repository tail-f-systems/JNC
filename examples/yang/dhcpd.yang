module dhcpd {
  namespace "http://tail-f.com/examples/dhcp/1.0";
  prefix dhcp;

  import ietf-inet-types {
    prefix inet;
  }
  import tailf-common {
    prefix tailf;
  }

  container dhcp {
    leaf defaultLeaseTime {
      type string;
      default PT600S;
    }
    leaf maxLeaseTime {
      type string;
      default PT7200S;
    }
    leaf logFacility {
      type loglevel;
      default local7;
    }
    container subNets {
      container subNet {
        uses subNetworkType;
      }
    }
    container sharedNetworks {
      list sharedNetwork {
        key name;
        max-elements 1024;
        leaf name {
          type string;
        }
        container subNets {
          tailf:java-class-name SharedSubNets;
          container subNet {
            uses subNetworkType;
            tailf:java-class-name SharedSubNet;
          }
        }
      }
    }
  }

  typedef loglevel {
    type enumeration {
      enum kern;
      enum mail;
      enum local7;
    }
  }

  grouping subNetworkType {
    leaf net {
      type inet:ip-address;
    }
    leaf mask {
      type inet:ip-address;
    }
    container range {
      presence "";
      leaf dynamicBootP {
        type boolean;
        default false;
      }
      leaf lowAddr {
        type inet:ip-address;
        mandatory true;
      }
      leaf hiAddr {
        type inet:ip-address;
      }
    }
    leaf routers {
      type string;
    }
    leaf maxLeaseTime {
      type string;
      default PT7200S;
    }
  }
}
