module simple {
  namespace "http://acme.example.com/simple";
  prefix "simple";
    
  revision 2008-02-21 {
    description "Second followup revision";
  }

  revision 2007-10-11 {
    description "First followup revision";
  }

  revision 2007-06-09 {
    description "Initial revision";
  }

  typedef mode-type {
    type enumeration {
      enum on;
      enum off;
      enum speed-stepping;
      // Adds an extra enumeration value "energy-saving"
      enum energy-saving;
    }
  }

  container config {
    leaf mode {
      type mode-type;
    }

    leaf d {
      type int32;
      default 55;
    }

    list newl {
      key x;
      leaf x {
        type int32;
      }
      leaf y {
        type int32;
      }
      // new optional leaf inside the list
      leaf z {
        type string;
      }
      
    }

    leaf host-metrics {
      type uint32 {
        // Expands the allowed value space
        range 0..256;
      }
    }
        
    container login {
      presence "";
      leaf message {
        type string;
      }

      list newl {
        key x;
        leaf x {
          type int32;
        }
        leaf y {
          type int32;
        }
      }



      // Adds a new optional leaf
      leaf monthly-message {
        type string;
      }
    }
  }
}
