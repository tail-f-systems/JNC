module recursive {
  namespace "http://acme.com/ns/recursive/1.0";
  prefix rec;
  
  typedef idValue {
    type string;
  }

  typedef tokenref {
    type leafref {
      path "/triggers/trigger/decision/token";
    }
  }
  
  container triggers {
    list trigger {
      key id;
      choice triggerType {
        case decision {
          uses decisionType;
        }
        case policy {
          uses policyType;
        }
      }
      uses idname;
    }
  }
  
  grouping decisionType {
    list decision {
      key token;
      leaf name {
        type string;
      }
      leaf token {
        type idValue;
      }
      list decision {
        key token;
        uses decisionSubType;
        list decision {
          key token;
          uses decisionSubType;
          list decision {
            key token;
            uses decisionSubType;
          }
        }
      }
    }
  }
  
  grouping policyType {
    container policy {
      uses decisionType;
      uses idname;
    }
  }
  
  grouping idname {
    leaf id {
      type idValue;
      mandatory true;
    }
    leaf name {
      type string;
      mandatory true;
    }
  }
  
  grouping telltype {
    leaf to {
      type string;
    }
    leaf tenant {
      type string;
    }
  }

  grouping decisionSubType {
    leaf name {
      type string;
    }
    leaf token {
      type tokenref;
    }
    container actions {
      list tell {
        key "to tenant";
        uses telltype;
      }
    }
  }
}
