module mini {
  namespace "http://example.com/ns/mini/1.0";
  prefix mini;
  typedef my-type {
    type string;
  }
  container c;
  container no-key {
    leaf-list ll {
      type my-type;
    }
  }
  list l {
    key k;
    leaf k {
      type string;
    }
  }
}
