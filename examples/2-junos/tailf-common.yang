module tailf-common {
  namespace "http://tail-f.com/yang/common";
  prefix tailf;


  organization "Tail-f Systems";

  description
    "This module contains two tweaks for the junos model, the xml schema
     that is returned from junos routers is not compatible with Yang";

  revision 2012-11-01 {
    description
      "Released as part of JNC 1.0.";
  }

  extension use-in {
    argument name;
    description
      "Specifies in which statements a particular extension statement can be
      used.";
  }


  extension junos-val-as-xml-tag {
    tailf:use-in "leaf";
    description
      "Internal extension to handle non-YANG JUNOS data models.
      Use only for key enumeration leafs.";
  }

  extension junos-val-with-prev-xml-tag {
    tailf:use-in "leaf";
    description
      "Internal extension to handle non-YANG JUNOS data models.
      Use only for keys where previous key is marked with
      tailf:junos-val-as-xml-tag.";
  }

  extension substatement {
    argument name;
    description
      "Specifies which statements can occur as substatement to the
      given statement.";
  }

  extension arg-type {
    tailf:substatement "type";
    description
      "Specifies the type of the argument.";
  }


  extension key-default {
    argument value {
      tailf:arg-type {
        type string;
      }
    }
    tailf:use-in "leaf";
    description
      "Must be used for key leafs only.

      Specifies a value that the CLI and WebUI will use when a list entry is
      created, and this key leaf is not given a value.

      If one key leaf has a key-default value, all key leafs that
      follow this key leaf must also have key-default values.";
  }

}
