module hosts {
  namespace "http://acme.com/ns/simple/1.0";
  prefix simple;
  import tailf-common {
      prefix tailf;
  }
  import ietf-inet-types {
    prefix inet;
  }
  typedef rej {
    type uint32 {
      range "0..1000";
    }
  }
  typedef conny {
    type rej {
      range "0..100";
    }
  }
  container hosts {
    list host {
      key name;
      max-elements 64;
      leaf name {
        type string;
      }
      leaf ip {
        type inet:ipv4-address;
      }
      leaf enabled {
        type boolean;
        default true;
      }
      leaf numberOfServers {
        type conny;
        mandatory true;
      }
      leaf-list domainA {
        type uint64;
      }
      leaf-list domainB {
        type string {
          pattern "a";
        }
      }
      leaf-list domainC {
        type conny;
      }
    }
    container sys {
      tailf:action restart {
        tailf:exec /tmp/action_script.sh {
	  tailf:args "-u $(user) -c $(context) -p $(path) -k $(keypath)";
          tailf:wd /tmp;
        }
        input {
          leaf mode {
            type string;
            mandatory true;
          }
          leaf debug {
            type empty;
          }
          container foo {
            presence "";
            leaf debug {
              type empty;
            }
          }
        }
        output {
          leaf res {
            type string;
            mandatory true;
          }
        }
      }
    }
  }
}
