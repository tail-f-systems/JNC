module simple {
  namespace "http://acme.com/ns/simple/1.0";
  prefix simple;
  container hosts {
    list host {
      key name;
      max-elements 64;
      leaf name {
        type string;
      }
      leaf enabled {
        type boolean;
        default true;
      }
      leaf numberOfServers {
        type uint32;
        mandatory true;
      }
    }
  }
}
