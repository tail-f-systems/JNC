// M3_BEGIN prolog
module simple {
  namespace "http://acme.example.com/simple";
  prefix "simple";
  
  revision 2007-10-11 {
    description "First followup revision";
  }
  
  revision 2007-06-09 {
    description "Initial revision";
  }
// M3_END prolog
  
  typedef mode-type {
    type enumeration {
      enum on;
      enum off;
      // Adds an extra enumeration value "speed-stepping"
      enum speed-stepping;
    }
  }
  
  container config {
    leaf mode {
      type mode-type;
    }

    leaf d {
      type int32;
      default 55;
    }

    leaf host-metrics {
      type uint32 {
        // Expands the allowed value space
        range 0..128;
      }
    }
    
    // Adds a new optional container
    container login {
      presence "";
      leaf message {
        type string;
      }

    }
  }
}
