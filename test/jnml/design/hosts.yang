module hosts {
  namespace "http://acme.example.com/simple/1.0";
  prefix "hosts";  
  organization "ACME Inc.";
  contact "average.joe@acme.example.com";
  description "The module for hosts implementing the ACME system.";
  
  revision 2007-11-26 {
    description "Initial revision.";
  }
  
  container hosts {
    list host {
      key "name";
      min-elements 0;
      max-elements 64;
      description "List of hosts in the system";
      leaf name {
        type string;
      }
      leaf enabled {
        type boolean;
        mandatory true;
      }
      container servers {
        presence true;
        list server {
          key "ip port";
          min-elements 0;
          unique "id";
          description "List of servers on the host";
          leaf ip {
            type string {
              length "7..15";
              pattern '(([0-1]?[0-9]?[0-9]|2[0-4][0-9]|25[0-5])\.){3}'
              +'([0-1]?[0-9]?[0-9]|2[0-4][0-9]|25[0-5])'
              +'(%[\p{N}\p{L}]+)?';
            }
          }
          leaf port {
            type portType;
          }
          leaf id {
            type string;
            mandatory true;
          }
          leaf qos {
            default "15192";
            type uint16;
          }
        }
      }
    }
  }
  typedef portType {
    type uint16 {
      range "1024..65535";
    }
  }
}
