module simple {
  namespace "http://tail-f.com/ns/simple";
  prefix simple;

    container zapp {
        list foo {
            key "app bar";
            leaf app {type string;}
            leaf bar {type string;}
            leaf saft {type string;}
        }
    }
}
