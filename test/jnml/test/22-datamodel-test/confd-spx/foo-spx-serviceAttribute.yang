submodule foo-spx-serviceAttribute {
    belongs-to foo-spx {
        prefix foo-spx;
    }

    import tailf-common {
        prefix tailf;
    }

    import foo-system {
        prefix foo-system;
    }

    // add new revision statements here

    revision 2011-01-06 {
        description "Conversion from confspec.";
    }


    /*  SPX service attributes are generic/readable names for various attributes 
        SPX looks for from RADIUS, LDAP and other interfaces. These are populated 
        automatically by SPX upon bootup. Examples of these are "userProfile",
        "ggsnIp" and "msisdn". We do NOT expect user to configure these. These 
        are simply for ease of configuration (e.g., CLI tab completion and 
        GUI drop down list) when configuring radius/attributeMap objects. These
        are intentionally not made into an enumeration as it should be possible
        to add to the list without upgrading confd database  */
    list serviceAttribute {
        key name;
        tailf:info "Foo service attribute list";

        leaf name {
            type foo-system:nameType;
            tailf:info "Foo service attribute";
        }
    }
}
