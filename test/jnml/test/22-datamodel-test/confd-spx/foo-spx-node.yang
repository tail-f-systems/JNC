submodule foo-spx-node {
    belongs-to foo-spx {
        prefix foo-spx;
    }

    import ietf-inet-types {
        prefix inet;
    }

    import tailf-common {
        prefix tailf;
    }

    import foo-topology {
        prefix foo-topology;
    }

    import foo-system {
        prefix foo-system;
    }

    // add new revision statements here

    revision 2011-01-06 {
        description "Conversion from confspec.";
    }


    augment "/foo-system:node" {
        /*  node identity  */
        list name {
            key name;
            max-elements 1;

            /*  Various identification parameters attached to this node  */
            leaf name {
                type foo-system:nonNullNameType;
                tailf:info "unique name of this SPX";
                must "count(/foo-topology:topology/foo-topology:spx[foo-topology:name=current()]) > 0" {
                    tailf:dependency '.';
                    tailf:dependency '/foo-topology:topology/foo-topology:spx';
                    error-message "node name must be a valid topology/spx[name]";
                }
            }
        }

        list cae {
            key name;
            config false;
            tailf:info "List of known CAEs";
            tailf:cdb-oper;

            leaf name {
                type string;
            }
            leaf ipAddr {
                type inet:ipv4-address;
            }
            leaf status {
                type string;
            }
            leaf lastHeartBeat {
                type uint32;
            }
            leaf incomingMessages {
                type uint64;
            }
            leaf outgoingMessages {
                type uint64;
            }
        }

        list session {
            key imsi;
            config false;
            tailf:cdb-oper;

            leaf imsi {
                type uint64;
            }
            leaf apn {
                type string;
            }
            leaf userIpAddr {
                type inet:ipv4-address;
            }
            leaf caeName {
                type string;
            }
            leaf state {
                type string;
            }
            leaf msisdn {
                type uint64;
            }
            leaf operatorId {
                type uint32;
            }
            leaf chargingId {
                type uint32;
            }
            leaf accountingId {
                type string;
            }
            leaf groupNames {
                type string;
            }
            leaf chargingPolicyType {
                type string;
            }
        }

        container sessionStatistics {
            config false;
            tailf:info "User Session Manager statistics";
            tailf:cdb-oper;

            leaf numSessionCreationAttemptsTotal {
                type uint64;
            }
            leaf numSessionCreationCompletionsTotal {
                type uint64;
            }
            leaf numSessionCreationFailuresTotal {
                type uint64;
            }
            leaf numSessionAllocationFailuresTotal {
                type uint64;
            }
            leaf numSessionInsertionFailuresTotal {
                type uint64;
            }
            leaf numCaeSessionCreations {
                type uint64;
            }
            leaf numRadiusSessionCreations {
                type uint64;
            }
            leaf numCaeSessionQueryRcvd {
                type uint64;
            }
            leaf numCaeDeleteSessionRcvd {
                type uint64;
            }
            leaf numCaeDeleteReqForNoSession {
                type uint64;
            }
            leaf numSuccessQueryRespSent {
                type uint64;
            }
            leaf numFailureQueryRespSent {
                type uint64;
            }
            leaf numSessionUpdatesSent {
                type uint64;
            }
            leaf numChargingReqSent {
                type uint64;
            }
            leaf numChargingRespSuccess {
                type uint64;
            }
            leaf numChargingRespFailures {
                type uint64;
            }
            leaf numChargingNoRespRecvd {
                type uint64;
            }
            leaf numChargingRespForNoSession {
                type uint64;
            }
            leaf numSessionGuardTimerExpired {
                type uint64;
            }
            leaf numSdbiRequestsSent {
                type uint64;
            }
            leaf numSdbiResponsesWithSuccess {
                type uint64;
            }
            leaf numSdbiResponsesWithFailure {
                type uint64;
            }
            leaf numSdbiTimerExpired {
                type uint64;
            }
        }
    }
}
