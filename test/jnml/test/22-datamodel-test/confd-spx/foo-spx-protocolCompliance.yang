submodule foo-spx-protocolCompliance {
    belongs-to foo-spx {
        prefix foo-spx;
    }

    import tailf-common {
        prefix tailf;
    }

    include foo-spx-types;

    // add new revision statements here

    revision 2011-01-06 {
        description "Conversion from confspec.";
    }


    container protocolCompliance {
        tailf:info "SPX Protocol Compliance Settings";

        leaf onlineCharging {
            type onlineChargingComplianceType;
            default gy;
            tailf:info "Protocol used for Online Charging";
        }
        leaf cdrFormat {
            type cdrFormatType;
            default 32.298;
            tailf:info "Format used for CDRs";
        }
        leaf defaultRatingGroup {
            type uint32;
            default 0;
            tailf:info "Default Credit Control Rating Group";
        }
        leaf serviceContextId {
            type string;
            default "default@foo.net";
            tailf:info "Service Context Id used with DIAMETER based credit control";
        }
        leaf defaultRulebase {
            type string;
            default "";
            tailf:info "The default Rulebase for online charging";
        }
        leaf chargingCharacteristics {
            type chargingCharacteristicsType;
            tailf:info "The charging characteristics flags as 4 hexadecimal digits representing a 16-bit field";
        }
    }
}
