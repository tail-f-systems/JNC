module foo-sdbi {
    namespace "http://foo.net/ns/foo-sdbi";
    prefix foo-sdbi;


    import ietf-inet-types {
        prefix inet;
    }

    import tailf-common {
        prefix tailf;
    }

    include foo-sdbi-types;

    organization "Foo Networks, Inc.";
    description  "Managed objects for SDBI.";

    // add new revision statements here

    revision 2011-01-06 {
        description "Conversion from confspec.";
    }


    container sdb {
        tailf:info "Subscriber Database interface configuration";

        container origin {
            tailf:info "Information about subsciber database server";

            leaf hostName {
                type string;
                default "";
                tailf:info "Arbitrary local hostname";
            }
            leaf ipAddr {
                type inet:ipv4-address;
                default 0.0.0.0;
                tailf:info "local IP address to listen on ";
            }
        }

        container server {
            tailf:info "Subscriber Database Server";

            list soap {
                key hostName;
                tailf:info "SOAP/XML based server";

                leaf hostName {
                    type string;
                    tailf:info "Arbitrary server hostname";
                }
                leaf url {
                    type string;
                    mandatory true;
                    tailf:info "SOAP server URL (HTTP)";
                }
                leaf method {
                    type sdbHttpMethod;
                    default post;
                    tailf:info "HTTP access method";
                }
                leaf requestFormat {
                    type string;
                    default "";
                    tailf:info "Request format for this server";
                }

                container responseXpath {
                    tailf:info "XPath information for various response elements";

                    leaf imsi {
                        type string;
                        default "";
                        tailf:info "xpath for imsi";
                    }
                    leaf msisdn {
                        type string;
                        default "";
                        tailf:info "xpath for msisdn";
                    }
                    leaf apn {
                        type string;
                        default "";
                        tailf:info "xpath for apn";
                    }
                    leaf profile {
                        type string;
                        default "";
                        tailf:info "xpath for profile";
                    }
                }

                container status {
                    config false;
                    tailf:info "Server Status";
                    tailf:cdb-oper;

                    leaf poolSize {
                        type uint64;
                        mandatory true;
                    }
                    leaf poolAllocs {
                        type uint64;
                        mandatory true;
                    }
                    leaf poolReuses {
                        type uint64;
                        mandatory true;
                    }
                    leaf poolReturns {
                        type uint64;
                        mandatory true;
                    }
                    leaf sdbRequests {
                        type uint64;
                        mandatory true;
                    }
                    leaf sdbResponses {
                        type uint64;
                        mandatory true;
                    }
                    leaf sdbSuccesses {
                        type uint64;
                        mandatory true;
                    }
                    leaf sdbTimeouts {
                        type uint64;
                        mandatory true;
                    }
                    leaf sdbFailures {
                        type uint64;
                        mandatory true;
                    }
                    leaf parseSuccesses {
                        type uint64;
                        mandatory true;
                    }
                    leaf parseFailures {
                        type uint64;
                        mandatory true;
                    }
                }
            }
            /*  when we support an LDAP server, it will go here  */
        }
    }
}
