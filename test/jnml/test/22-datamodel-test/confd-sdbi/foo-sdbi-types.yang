submodule foo-sdbi-types {
    belongs-to foo-sdbi {
        prefix foo-sdbi;
    }
    
    // add new revision statements here

    revision 2011-01-06 {
        description "Conversion from confspec.";
    }


    typedef nameType {
        type string {
            length "min .. 63";
        }
    }

    typedef heartBeatIntervalType {
        type uint16 {
            range "0 .. 3600";
        }
    }

    typedef sdbHttpMethod {
        type enumeration {
            enum get;
            enum post;
        }
    }
}
