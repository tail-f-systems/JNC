module foo-alarm {
    namespace "http://foo.net/ns/foo-alarm";
    prefix foo-alarm;

    import ietf-yang-types {
        prefix yang;
    }

    import tailf-common {
        prefix tailf;
    }

    include foo-alarm-types;

    organization "Foo Networks, Inc.";
    description  "Managed objects for alarms.";

    // add new revision statements here

    revision 2011-01-06 {
        description "Conversion from confspec.";
    }


    container alarm {
        container summary {
            config false;
            tailf:cdb-oper;

            leaf severity {
                type alarmSeverityType;
                mandatory true;
            }
            leaf previousSeverity {
                type alarmSeverityType;
                mandatory true;
            }
            leaf lastChange {
                type yang:date-and-time;
                mandatory true;
            }
        }

        list active {
            key "severity occurrence category alarmId xpath";
            config false;
            tailf:cdb-oper;

            leaf severity {
                type alarmSeverityType;
            }
            leaf occurrence {
                type yang:date-and-time;
            }
            leaf category {
                type alarmCategoryType;
            }
            leaf alarmId {
                type alarmIdType;
            }
            leaf xpath {
                type string;
            }
            leaf value {
                type string;
            }
            leaf extra {
                type string;
            }
        }

        leaf snmpFilter {
            type alarmSeverityType;
            default minor;
            tailf:info "Send SNMP traps for alarms at or above this severity";
        }

        container system {
            container linkDown {
                tailf:info "Critical boolean alarm for /ip/interface[name]/status/operStatus";
                uses booleanAlarmConfig {
                    refine "setSoakSeconds" {
                        default 0;
                    }
                }
            }

            container atmControllerDown {
                tailf:info "Major boolean alarm for /atm/controller[slot][subSlot]/status/operStatus";
                uses booleanAlarmConfig {
                    refine "setSoakSeconds" {
                        default 0;
                    }
                }
            }

            container atmPortDown {
                tailf:info "Major boolean alarm for /atm/port[slot][subSlot][port]/status/operStatus";
                uses booleanAlarmConfig {
                    refine "setSoakSeconds" {
                        default 0;
                    }
                }
            }

            container atmPortUtilizationWarning {
                tailf:info "Minor gauge alarm for /atm/port[slot][subSlot][port]/counters/utilization";
                uses gaugeAlarmConfig {
                    refine "setThreshold" {
                        default 75;
                    }
                    refine "clearThreshold" {
                        default 65;
                    }
                }

                /* clearThreshold <= setThreshold  */
                must "clearThreshold <= setThreshold" {
                    tailf:dependency '.';
                    error-message "atmPortUtilizationWarning clearThreshold must be <= setThreshold";
                }
            }

            container atmPortUtilization {
                tailf:info "Major gauge alarm for /atm/port[slot][subSlot][port]/counters/utilization";
                uses gaugeAlarmConfig {
                    refine "setThreshold" {
                        default 85;
                    }
                    refine "clearThreshold" {
                        default 75;
                    }
                }

                /*  clearThreshold <= setThreshold  */
                must "clearThreshold <= setThreshold" {
                    tailf:dependency '.';
                    error-message "atmPortUtilization clearThreshold must be <= setThreshold";
                }
            }

            /*  atmPortUtilizationWarning thresholds <= atmPortUtilization thresholds  */
            must "atmPortUtilizationWarning/setThreshold <= atmPortUtilization/setThreshold" {
                tailf:dependency 'atmPortUtilizationWarning/setThreshold';
                tailf:dependency 'atmPortUtilization/setThreshold';
                error-message "atmPortUtilizationWarning/setThreshold must be <= atmPortUtilization/setThreshold";
            }
            must "atmPortUtilizationWarning/clearThreshold <= atmPortUtilization/clearThreshold" {
                tailf:dependency 'atmPortUtilizationWarning/clearThreshold';
                tailf:dependency 'atmPortUtilization/clearThreshold';
                error-message "atmPortUtilizationWarning/clearThreshold must be <= atmPortUtilization/clearThreshold";
            }

            container applicationFailure {
                tailf:info "Critical boolean alarm for /node/application[slot][name]/operStatus";
                uses booleanAlarmConfig {
                    refine "setSoakSeconds" {
                        default 0;
                    }
                    refine "clearSoakSeconds" {
                        default 0;
                    }
                }
            }

            container internalCommsFailure {
                tailf:info "Critical boolean alarm for /node";
                uses booleanAlarmConfig {
                    refine "setSoakSeconds" {
                        default 60;
                    }
                    refine "clearSoakSeconds" {
                        default 60;
                    }
                }
            }

            container watchdogFailure {
                tailf:info "Critical boolean event for /card[slot]/status/operStatus";
                uses booleanAlarmConfig {
                    refine "setSoakSeconds" {
                        default 0;
                    }
                    refine "clearSoakSeconds" {
                        default 0;
                    }
                }
            }

            container memoryUtilizationWarning {
                tailf:info "Minor gauge alarm for /card[slot]/status/memoryUtilization";
                uses gaugeAlarmConfig {
                    refine "setThreshold" {
                        default 80;
                    }
                    refine "clearThreshold" {
                        default 70;
                    }
                }

                /*  clearThreshold <= setThreshold  */
                must "clearThreshold <= setThreshold" {
                    tailf:dependency '.';
                    error-message "memoryPortUtilizationWarning clearThreshold must be <= setThreshold";
                }
            }

            container memoryUtilization {
                tailf:info "Major gauge alarm for /card[slot]/status/memoryUtilization";
                uses gaugeAlarmConfig {
                    refine "setThreshold" {
                        default 90;
                    }
                    refine "clearThreshold" {
                        default 80;
                    }
                }

                /*  clearThreshold <= setThreshold  */
                must "clearThreshold <= setThreshold" {
                    tailf:dependency '.';
                    error-message "memoryPortUtilizationWarning clearThreshold must be <= setThreshold";
                }
            }

            /*  memoryUtilizationWarning thresholds <= memoryUtilization thresholds  */
            must "memoryUtilizationWarning/setThreshold <= memoryUtilization/setThreshold" {
                tailf:dependency 'memoryUtilizationWarning/setThreshold';
                tailf:dependency 'memoryUtilization/setThreshold';
                error-message "memoryUtilizationWarning/setThreshold must be <= memoryUtilization/setThreshold";
            }
            must "memoryUtilizationWarning/clearThreshold <= memoryUtilization/clearThreshold" {
                tailf:dependency 'memoryUtilizationWarning/clearThreshold';
                tailf:dependency 'memoryUtilization/clearThreshold';
                error-message "memoryUtilizationWarning/clearThreshold must be <= memoryUtilization/clearThreshold";
            }

            container cpuUtilizationWarning {
                tailf:info "Minor gauge alarm for /card[slot]/status/cpuUtilization";
                uses gaugeAlarmConfig {
                    refine "setThreshold" {
                        default 80;
                    }
                    refine "clearThreshold" {
                        default 70;
                    }
                }

                /*  clearThreshold <= setThreshold  */
                must "clearThreshold <= setThreshold" {
                    tailf:dependency '.';
                    error-message "cpuUtilizationWarning clearThreshold must be <= setThreshold";
                }
            }

            container cpuUtilization {
                tailf:info "Major gauge alarm for /card[slot]/status/cpuUtilization";
                uses gaugeAlarmConfig {
                    refine "setThreshold" {
                        default 90;
                    }
                    refine "clearThreshold" {
                        default 80;
                    }
                }

                /*  clearThreshold <= setThreshold  */
                must "clearThreshold <= setThreshold" {
                    tailf:dependency '.';
                    error-message "cpuUtilizationWarning clearThreshold must be <= setThreshold";
                }
            }

            /*  cpuUtilizationWarning thresholds <= cpuUtilization thresholds  */
            must "cpuUtilizationWarning/setThreshold <= cpuUtilization/setThreshold" {
                tailf:dependency 'cpuUtilizationWarning/setThreshold';
                tailf:dependency 'cpuUtilization/setThreshold';
                error-message "cpuUtilizationWarning/setThreshold must be <= cpuUtilization/setThreshold";
            }
            must "cpuUtilizationWarning/clearThreshold <= cpuUtilization/clearThreshold" {
                tailf:dependency 'cpuUtilizationWarning/clearThreshold';
                tailf:dependency 'cpuUtilization/clearThreshold';
                error-message "cpuUtilizationWarning/clearThreshold must be <= cpuUtilization/clearThreshold";
            }

            container diskUtilizationWarning {
                tailf:info "Minor gauge alarm for /card[slot]/disk[name]/partition[name]/utilization";
                uses gaugeAlarmConfig {
                    refine "setThreshold" {
                        default 85;
                    }
                    refine "clearThreshold" {
                        default 75;
                    }
                }

                /*  clearThreshold <= setThreshold  */
                must "clearThreshold <= setThreshold" {
                    tailf:dependency '.';
                    error-message "diskUtilizationWarning clearThreshold must be <= setThreshold";
                }
            }

            container diskUtilization {
                tailf:info "Major gauge alarm for /card[slot]/disk[name]/partition[name]/utilization";
                uses gaugeAlarmConfig {
                    refine "setThreshold" {
                        default 85;
                    }
                    refine "clearThreshold" {
                        default 75;
                    }
                }

                /*  clearThreshold <= setThreshold  */
                must "clearThreshold <= setThreshold" {
                    tailf:dependency '.';
                    error-message "diskUtilizationWarning clearThreshold must be <= setThreshold";
                }
            }

            /*  diskUtilizationWarning thresholds <= diskUtilization thresholds  */
            must "diskUtilizationWarning/setThreshold <= diskUtilization/setThreshold" {
                tailf:dependency 'diskUtilizationWarning/setThreshold';
                tailf:dependency 'diskUtilization/setThreshold';
                error-message "diskUtilizationWarning/setThreshold must be <= diskUtilization/setThreshold";
            }
            must "diskUtilizationWarning/clearThreshold <= diskUtilization/clearThreshold" {
                tailf:dependency 'diskUtilizationWarning/clearThreshold';
                tailf:dependency 'diskUtilization/clearThreshold';
                error-message "diskUtilizationWarning/clearThreshold must be <= diskUtilization/clearThreshold";
            }

            container interfaceUtilizationWarning {
                tailf:info "Minor gauge alarm for /ip/interface[name]/status/utilization";
                uses gaugeAlarmConfig {
                    refine "setThreshold" {
                        default 80;
                    }
                    refine "clearThreshold" {
                        default 70;
                    }
                }

                /*  clearThreshold <= setThreshold  */
                must "clearThreshold <= setThreshold" {
                    tailf:dependency '.';
                    error-message "interfaceUtilizationWarning clearThreshold must be <= setThreshold";
                }
            }

            container interfaceUtilization {
                tailf:info "Major gauge alarm for /ip/interface[name]/status/utilization";
                uses gaugeAlarmConfig {
                    refine "setThreshold" {
                        default 90;
                    }
                    refine "clearThreshold" {
                        default 80;
                    }
                }

                /*  clearThreshold <= setThreshold  */
                must "clearThreshold <= setThreshold" {
                    tailf:dependency '.';
                    error-message "interfaceUtilizationWarning clearThreshold must be <= setThreshold";
                }
            }

            /*  interfaceUtilizationWarning thresholds <= interfaceUtilization thresholds  */
            must "interfaceUtilizationWarning/setThreshold <= interfaceUtilization/setThreshold" {
                tailf:dependency 'interfaceUtilizationWarning/setThreshold';
                tailf:dependency 'interfaceUtilization/setThreshold';
                error-message "interfaceUtilizationWarning/setThreshold must be <= interfaceUtilization/setThreshold";
            }
            must "interfaceUtilizationWarning/clearThreshold <= interfaceUtilization/clearThreshold" {
                tailf:dependency 'interfaceUtilizationWarning/clearThreshold';
                tailf:dependency 'interfaceUtilization/clearThreshold';
                error-message "interfaceUtilizationWarning/clearThreshold must be <= interfaceUtilization/clearThreshold";
            }

            container interfaceRxPps {
                tailf:info "Major rate alarm for /ip/interface[name]/counters/txPkts";
                uses rateAlarmConfig {
                    refine "setThreshold" {
                        default 50000;
                    }
                    refine "clearThreshold" {
                        default 40000;
                    }
                }

                /*  clearThreshold <= setThreshold  */
                must "clearThreshold <= setThreshold" {
                    tailf:dependency '.';
                    error-message "interfaceRxPps clearThreshold must be <= setThreshold";
                }
            }

            container interfaceTxPps {
                tailf:info "Major rate alarm for /ip/interface[name]/counters/txPkts";
                uses rateAlarmConfig {
                    refine "setThreshold" {
                        default 50000;
                    }
                    refine "clearThreshold" {
                        default 40000;
                    }
                }

                /*  clearThreshold <= setThreshold  */
                must "clearThreshold <= setThreshold" {
                    tailf:dependency '.';
                    error-message "interfaceTxPps clearThreshold must be <= setThreshold";
                }
            }

            container interfaceLowRxPps {
                tailf:info "Major inverse rate alarm for /ip/interface[name]/counters/rxPkts";
                uses rateAlarmConfig {
                    refine "setThreshold" {
                        default 10;
                    }
                    refine "clearThreshold" {
                        default 100;
                    }
                }

                /*  clearThreshold >= setThreshold  */
                must "clearThreshold >= setThreshold" {
                    tailf:dependency '.';
                    error-message "interfaceLowRxPps clearThreshold must be >= setThreshold";
                }
            }

            container interfaceLowTxPps {
                tailf:info "Major inverse rate alarm for network /ip/interface[name]/counters/txPkts";
                uses rateAlarmConfig {
                    refine "setThreshold" {
                        default 10;
                    }
                    refine "clearThreshold" {
                        default 100;
                    }
                }

                /*  clearThreshold >= setThreshold  */
                must "clearThreshold >= setThreshold" {
                    tailf:dependency '.';
                    error-message "interfaceLowTxPps clearThreshold must be >= setThreshold";
                }
            }

            container interfaceRxPktDropWarning {
                tailf:info "Minor rate alarm for /ip/interface[name]/counters/rxDropped";
                uses rateAlarmConfig {
                    refine "setThreshold" {
                        default 10;
                    }
                    refine "clearThreshold" {
                        default 5;
                    }
                }

                /*  clearThreshold <= setThreshold  */
                must "clearThreshold <= setThreshold" {
                    tailf:dependency '.';
                    error-message "interfaceRxPktDropWarning clearThreshold must be <= setThreshold";
                }
            }

            container interfaceRxPktDrop {
                tailf:info "Major rate alarm for /ip/interface[name]/counters/rxDropped";
                uses rateAlarmConfig {
                    refine "setThreshold" {
                        default 100;
                    }
                    refine "clearThreshold" {
                        default 10;
                    }
                }

                /*  clearThreshold <= setThreshold  */
                must "clearThreshold <= setThreshold" {
                    tailf:dependency '.';
                    error-message "interfaceRxPktDrop clearThreshold must be <= setThreshold";
                }
            }

            /*  interfaceRxPktDropWarning thresholds <= interfaceRxPktDrop thresholds  */
            must "interfaceRxPktDropWarning/setThreshold <= interfaceRxPktDrop/setThreshold" {
                tailf:dependency 'interfaceRxPktDropWarning/setThreshold';
                tailf:dependency 'interfaceRxPktDrop/setThreshold';
                error-message "interfaceRxPktDropWarning/setThreshold must be <= interfaceRxPktDrop/setThreshold";
            }
            must "interfaceRxPktDropWarning/clearThreshold <= interfaceRxPktDrop/clearThreshold" {
                tailf:dependency 'interfaceRxPktDropWarning/clearThreshold';
                tailf:dependency 'interfaceRxPktDrop/clearThreshold';
                error-message "interfaceRxPktDropWarning/clearThreshold must be <= interfaceRxPktDrop/clearThreshold";
            }

            container interfaceTxPktDropWarning {
                tailf:info "Minor rate alarm for /ip/interface[name]/counters/txDropped";
                uses rateAlarmConfig {
                    refine "setThreshold" {
                        default 10;
                    }
                    refine "clearThreshold" {
                        default 5;
                    }
                }

                /*  clearThreshold <= setThreshold  */
                must "clearThreshold <= setThreshold" {
                    tailf:dependency '.';
                    error-message "interfaceTxPktDropWarning clearThreshold must be <= setThreshold";
                }
            }

            container interfaceTxPktDrop {
                tailf:info "Major rate alarm for /ip/interface[name]/counters/txDropped";
                uses rateAlarmConfig {
                    refine "setThreshold" {
                        default 100;
                    }
                    refine "clearThreshold" {
                        default 10;
                    }
                }

                /*  clearThreshold <= setThreshold  */
                must "clearThreshold <= setThreshold" {
                    tailf:dependency '.';
                    error-message "interfaceTxPktDropWarning clearThreshold must be <= setThreshold";
                }
            }

            /*  interfaceTxPktDropWarning thresholds <= interfaceTxPktDrop thresholds  */
            must "interfaceTxPktDropWarning/setThreshold <= interfaceTxPktDrop/setThreshold" {
                tailf:dependency 'interfaceTxPktDropWarning/setThreshold';
                tailf:dependency 'interfaceTxPktDrop/setThreshold';
                error-message "interfaceTxPktDropWarning/setThreshold must be <= interfaceTxPktDrop/setThreshold";
            }
            must "interfaceTxPktDropWarning/clearThreshold <= interfaceTxPktDrop/clearThreshold" {
                tailf:dependency 'interfaceTxPktDropWarning/clearThreshold';
                tailf:dependency 'interfaceTxPktDrop/clearThreshold';
                error-message "interfaceTxPktDropWarning/clearThreshold must be <= interfaceTxPktDrop/clearThreshold";
            }

            container networkRxPpsWarning {
                tailf:info "Minor rate alarm for SUM(/ip/interface[name]/counters/rxPkts)";
                uses rateAlarmConfig {
                    refine "setThreshold" {
                        default 160000;
                    }
                    refine "clearThreshold" {
                        default 120000;
                    }
                }

                /*  clearThreshold <= setThreshold  */
                must "clearThreshold <= setThreshold" {
                    tailf:dependency '.';
                    error-message "networkRxPpsWarning clearThreshold must be <= setThreshold";
                }
            }

            container networkRxPps {
                tailf:info "Major rate alarm for SUM(/ip/interface[name]/counters/rxPkts)";
                uses rateAlarmConfig {
                    refine "setThreshold" {
                        default 200000;
                    }
                    refine "clearThreshold" {
                        default 160000;
                    }
                }

                /*  clearThreshold <= setThreshold  */
                must "clearThreshold <= setThreshold" {
                    tailf:dependency '.';
                    error-message "networkRxPps clearThreshold must be <= setThreshold";
                }
            }

            /*  networkRxPpsWarning thresholds <= networkRxPps thresholds  */
            must "networkRxPpsWarning/setThreshold <= networkRxPps/setThreshold" {
                tailf:dependency 'networkRxPpsWarning/setThreshold';
                tailf:dependency 'networkRxPps/setThreshold';
                error-message "networkRxPpsWarning/setThreshold must be <= networkRxPps/setThreshold";
            }
            must "networkRxPpsWarning/clearThreshold <= networkRxPps/clearThreshold" {
                tailf:dependency 'networkRxPpsWarning/clearThreshold';
                tailf:dependency 'networkRxPps/clearThreshold';
                error-message "networkRxPpsWarning/clearThreshold must be <= networkRxPps/clearThreshold";
            }

            container networkTxPpsWarning {
                tailf:info "Minor rate alarm for SUM(/ip/interface[name]/counters/txPkts)";
                uses rateAlarmConfig {
                    refine "setThreshold" {
                        default 160000;
                    }
                    refine "clearThreshold" {
                        default 120000;
                    }
                }

                /*  clearThreshold <= setThreshold  */
                must "clearThreshold <= setThreshold" {
                    tailf:dependency '.';
                    error-message "networkTxPpsWarning clearThreshold must be <= setThreshold";
                }
            }

            container networkTxPps {
                tailf:info "Major rate alarm for SUM(/ip/interface[name]/counters/txPkts)";
                uses rateAlarmConfig {
                    refine "setThreshold" {
                        default 200000;
                    }
                    refine "clearThreshold" {
                        default 160000;
                    }
                }

                /*  clearThreshold <= setThreshold  */
                must "clearThreshold <= setThreshold" {
                    tailf:dependency '.';
                    error-message "networkTxPps clearThreshold must be <= setThreshold";
                }
            }

            /*  networkTxPpsWarning thresholds <= networkTxPps thresholds  */
            must "networkTxPpsWarning/setThreshold <= networkTxPps/setThreshold" {
                tailf:dependency 'networkTxPpsWarning/setThreshold';
                tailf:dependency 'networkTxPps/setThreshold';
                error-message "networkTxPpsWarning/setThreshold must be <= networkTxPps/setThreshold";
            }
            must "networkTxPpsWarning/clearThreshold <= networkTxPps/clearThreshold" {
                tailf:dependency 'networkTxPpsWarning/clearThreshold';
                tailf:dependency 'networkTxPps/clearThreshold';
                error-message "networkTxPpsWarning/clearThreshold must be <= networkTxPps/clearThreshold";
            }

            container networkLowTxPps {
                tailf:info "Major inverse rate alarm for SUM(/ip/interface[name]/counters/txPkts)";
                uses rateAlarmConfig {
                    refine "setThreshold" {
                        default 10;
                    }
                    refine "clearThreshold" {
                        default 100;
                    }
                }

                /*  clearThreshold >= setThreshold  */
                must "clearThreshold >= setThreshold" {
                    tailf:dependency '.';
                    error-message "networkLowTxPps clearThreshold must be >= setThreshold";
                }
            }

            container networkLowRxPps {
                tailf:info "Major inverse rate alarm for SUM(/ip/interface[name]/counters/rxPkts)";
                uses rateAlarmConfig {
                    refine "setThreshold" {
                        default 10;
                    }
                    refine "clearThreshold" {
                        default 100;
                    }
                }

                /*  clearThreshold >= setThreshold  */
                must "clearThreshold >= setThreshold" {
                    tailf:dependency '.';
                    error-message "networkLowRxPps clearThreshold must be >= setThreshold";
                }
            }

            container obsPowerFailure {
                tailf:info "Critical boolean alarm for /node/obu[id]/powerSupply[id]/operStatus";
                uses booleanAlarmConfig {
                    refine "setSoakSeconds" {
                        default 0;
                    }
                }
            }

            container obsSwitchFailure {
                tailf:info "Critical boolean alarm for /node/obu[id]/switchFailure[id]/operStatus";
                uses booleanAlarmConfig {
                    refine "setSoakSeconds" {
                        default 0;
                    }
                }
            }

            container obsDown {
                tailf:info "Critical boolean alarm for /node/obs[id]/operStatus";
                uses booleanAlarmConfig {
                    refine "setSoakSeconds" {
                        default 0;
                    }
                }
            }

            container obsBypassActive {
                tailf:info "Critical boolean alarm for /node/obs[id]/status";
                uses booleanAlarmConfig {
                    refine "setSoakSeconds" {
                        default 0;
                    }
                }
            }

            container hddTransactionRateWarning {
                tailf:info "Minor gauge alarm for /card[slot]/disk[name]";
                uses gaugeAlarmConfig {
                    refine "setThreshold" {
                        default 200;
                    }
                    refine "clearThreshold" {
                        default 160;
                    }
                    refine "setSoakSeconds" {
                        default 30;
                    }
                    refine "clearSoakSeconds" {
                        default 15;
                    }
                }

                /*  clearThreshold <= setThreshold  */
                must "clearThreshold <= setThreshold" {
                    tailf:dependency '.';
                    error-message "hddTransactionRateWarning clearThreshold must be <= setThreshold";
                }
            }

            container hddTransactionRate {
                tailf:info "Major gauge alarm for /card[slot]/disk[name]";
                uses gaugeAlarmConfig {
                    refine "setThreshold" {
                        default 240;
                    }
                    refine "clearThreshold" {
                        default 200;
                    }
                    refine "setSoakSeconds" {
                        default 60;
                    }
                    refine "clearSoakSeconds" {
                        default 30;
                    }
                }

                /*  clearThreshold <= setThreshold  */
                must "clearThreshold <= setThreshold" {
                    tailf:dependency '.';
                    error-message "hddTransactionRate clearThreshold must be <= setThreshold";
                }
            }

            /*  hddTransactionRateWarning thresholds <= hddTransactionRate thresholds  */
            must "hddTransactionRateWarning/setThreshold <= hddTransactionRate/setThreshold" {
                tailf:dependency 'hddTransactionRateWarning/setThreshold';
                tailf:dependency 'hddTransactionRate/setThreshold';
                error-message "hddTransactionRateWarning/setThreshold must be <= hddTransactionRate/setThreshold";
            }
            must "hddTransactionRateWarning/clearThreshold <= hddTransactionRate/clearThreshold" {
                tailf:dependency 'hddTransactionRateWarning/clearThreshold';
                tailf:dependency 'hddTransactionRate/clearThreshold';
                error-message "hddTransactionRateWarning/clearThreshold must be <= hddTransactionRate/clearThreshold";
            }

            container ssdReadTransactionRateWarning {
                tailf:info "Minor gauge alarm for /card[slot]/disk[name]";
                uses gaugeAlarmConfig {
                    refine "setThreshold" {
                        default 1200;
                    }
                    refine "clearThreshold" {
                        default 1000;
                    }
                    refine "setSoakSeconds" {
                        default 30;
                    }
                    refine "clearSoakSeconds" {
                        default 15;
                    }
                }

                /*  clearThreshold <= setThreshold  */
                must "clearThreshold <= setThreshold" {
                    tailf:dependency '.';
                    error-message "ssdReadTransactionRateWarning clearThreshold must be <= setThreshold";
                }
            }

            container ssdReadTransactionRate {
                tailf:info "Major gauge alarm for /card[slot]/disk[name]";
                uses gaugeAlarmConfig {
                    refine "setThreshold" {
                        default 1500;
                    }
                    refine "clearThreshold" {
                        default 1200;
                    }
                    refine "setSoakSeconds" {
                        default 60;
                    }
                    refine "clearSoakSeconds" {
                        default 30;
                    }
                }

                /*  clearThreshold <= setThreshold  */
                must "clearThreshold <= setThreshold" {
                    tailf:dependency '.';
                    error-message "ssdReadTransactionRate clearThreshold must be <= setThreshold";
                }
            }

            /*  ssdReadTransactionRateWarning thresholds <= ssdReadTransactionRate thresholds  */
            must "ssdReadTransactionRateWarning/setThreshold <= ssdReadTransactionRate/setThreshold" {
                tailf:dependency 'ssdReadTransactionRateWarning/setThreshold';
                tailf:dependency 'ssdReadTransactionRate/setThreshold';
                error-message "ssdReadTransactionRateWarning/setThreshold must be <= ssdReadTransactionRate/setThreshold";
            }
            must "ssdReadTransactionRateWarning/clearThreshold <= ssdReadTransactionRate/clearThreshold" {
                tailf:dependency 'ssdReadTransactionRateWarning/clearThreshold';
                tailf:dependency 'ssdReadTransactionRate/clearThreshold';
                error-message "ssdReadTransactionRateWarning/clearThreshold must be <= ssdReadTransactionRate/clearThreshold";
            }

            container ssdWriteTransactionRateWarning {
                tailf:info "Minor gauge alarm for /card[slot]/disk[name]/utilization";
                uses gaugeAlarmConfig {
                    refine "setThreshold" {
                        default 100;
                    }
                    refine "clearThreshold" {
                        default 80;
                    }
                    refine "setSoakSeconds" {
                        default 30;
                    }
                    refine "clearSoakSeconds" {
                        default 15;
                    }
                }

                /*  clearThreshold <= setThreshold  */
                must "clearThreshold <= setThreshold" {
                    tailf:dependency '.';
                    error-message "ssdWriteTransactionRateWarning clearThreshold must be <= setThreshold";
                }
            }

            container ssdWriteTransactionRate {
                tailf:info "Major gauge alarm for /card[slot]/disk[name]/utilization";
                uses gaugeAlarmConfig {
                    refine "setThreshold" {
                        default 120;
                    }
                    refine "clearThreshold" {
                        default 100;
                    }
                    refine "setSoakSeconds" {
                        default 60;
                    }
                    refine "clearSoakSeconds" {
                        default 30;
                    }
                }

                /*  clearThreshold <= setThreshold  */
                must "clearThreshold <= setThreshold" {
                    tailf:dependency '.';
                    error-message "ssdWriteTransactionRate clearThreshold must be <= setThreshold";
                }
            }

            /*  ssdWriteTransactionRateWarning thresholds <= ssdWriteTransactionRate thresholds  */
            must "ssdWriteTransactionRateWarning/setThreshold <= ssdWriteTransactionRate/setThreshold" {
                tailf:dependency 'ssdWriteTransactionRateWarning/setThreshold';
                tailf:dependency 'ssdWriteTransactionRate/setThreshold';
                error-message "ssdWriteTransactionRateWarning/setThreshold must be <= ssdWriteTransactionRate/setThreshold";
            }
            must "ssdWriteTransactionRateWarning/clearThreshold <= ssdWriteTransactionRate/clearThreshold" {
                tailf:dependency 'ssdWriteTransactionRateWarning/clearThreshold';
                tailf:dependency 'ssdWriteTransactionRate/clearThreshold';
                error-message "ssdWriteTransactionRateWarning/clearThreshold must be <= ssdWriteTransactionRate/clearThreshold";
            }

            container resourceControl {
                tailf:info "Major boolean alarm for /card[slot]/application[name]";
                uses booleanAlarmConfig {
                    refine "setSoakSeconds" {
                        default 0;
                    }
                    refine "clearSoakSeconds" {
                        default 0;
                    }
                }
            }

            container haTransition {
                tailf:info "Critical boolean alarm for protective App HA State Transition";
                uses booleanAlarmConfig {
                    refine "setSoakSeconds" {
                        default 0;
                    }
                }
            }
        }

        container chassis {
            container temperatureLow {
                tailf:info "Minor inverse gauge alarm for /card[slot]/status/temperature";
                uses gaugeAlarmConfig {
                    refine "setThreshold" {
                        default 5;
                    }
                    refine "clearThreshold" {
                        default 10;
                    }
                }

                /*  clearThreshold >= setThreshold  */
                must "clearThreshold >= setThreshold" {
                    tailf:dependency '.';
                    error-message "temperatureLow clearThreshold must be >= setThreshold";
                }
            }

            container temperatureHighWarning {
                tailf:info "Major gauge alarm for /card[slot]/status/temperature";
                uses gaugeAlarmConfig {
                    refine "setThreshold" {
                        default 50;
                    }
                    refine "clearThreshold" {
                        default 40;
                    }
                }

                /*  clearThreshold <= setThreshold  */
                must "clearThreshold <= setThreshold" {
                    tailf:dependency '.';
                    error-message "temperatureHighWarning clearThreshold must be <= setThreshold";
                }
            }

            container temperatureHigh {
                tailf:info "Critical gauge alarm for /card[slot]/status/temperature";
                uses gaugeAlarmConfig {
                    refine "setThreshold" {
                        default 70;
                    }
                    refine "clearThreshold" {
                        default 60;
                    }
                }

                /*  clearThreshold <= setThreshold  */
                must "clearThreshold <= setThreshold" {
                    tailf:dependency '.';
                    error-message "temperatureHigh clearThreshold must be <= setThreshold";
                }
            }

            /*  temperatureHigh thresholds < temperatureHighWarning thresholds  */
            must "temperatureHighWarning/setThreshold <= temperatureHigh/setThreshold" {
                tailf:dependency 'temperatureHighWarning/setThreshold';
                tailf:dependency 'temperatureHigh/setThreshold';
                error-message "temperatureHighWarning/setThreshold must be <= temperatureHigh/setThreshold";
            }
            must "temperatureHighWarning/clearThreshold <= temperatureHigh/clearThreshold" {
                tailf:dependency 'temperatureHighWarning/clearThreshold';
                tailf:dependency 'temperatureHigh/clearThreshold';
                error-message "temperatureHighWarning/clearThreshold must be <= temperatureHigh/clearThreshold";
            }

            /*  temperatureLow thresholds < temperatureHigh thresholds  */
            must "temperatureLow/setThreshold <= temperatureHigh/setThreshold" {
                tailf:dependency 'temperatureLow/setThreshold';
                tailf:dependency 'temperatureHigh/setThreshold';
                error-message "temperatureLow/setThreshold must be <= temperatureHigh/setThreshold";
            }
            must "temperatureLow/clearThreshold <= temperatureHigh/clearThreshold" {
                tailf:dependency 'temperatureLow/clearThreshold';
                tailf:dependency 'temperatureHigh/clearThreshold';
                error-message "temperatureLow/clearThreshold must be <= temperatureHigh/clearThreshold";
            }

            container powerSupplyRemoved {
                tailf:info "Minor boolean alarm for /card[slot]/powerSupply[id]/present";
                uses booleanAlarmConfig {
                    refine "setSoakSeconds" {
                        default 0;
                    }
                    refine "clearSoakSeconds" {
                        default 60;
                    }
                }
            }

            container powerSupplyFailed {
                tailf:info "Minor boolean alarm for /card[slot]/powerSupply[id]/operStatus";
                uses booleanAlarmConfig {
                    refine "setSoakSeconds" {
                        default 0;
                    }
                    refine "clearSoakSeconds" {
                        default 60;
                    }
                }
            }

            container fanRemoved {
                tailf:info "Minor boolean alarm for /card[slot]/fan[id]/present";
                uses booleanAlarmConfig {
                    refine "setSoakSeconds" {
                        default 0;
                    }
                    refine "clearSoakSeconds" {
                        default 60;
                    }
                }
            }

            container fanFailed {
                tailf:info "Minor boolean alarm for /card[slot]/fan[id]/operStatus";
                uses booleanAlarmConfig {
                    refine "setSoakSeconds" {
                        default 0;
                    }
                    refine "clearSoakSeconds" {
                        default 60;
                    }
                }
            }

            container diskRemoved {
                tailf:info "Minor boolean alarm for /card[slot]/disk[name]/device[id]/present";
                uses booleanAlarmConfig {
                    refine "setSoakSeconds" {
                        default 0;
                    }
                    refine "clearSoakSeconds" {
                        default 60;
                    }
                }
            }

            container diskFailed {
                tailf:info "Minor boolean alarm for /card[slot]/disk[name]/device[id]/operStatus";
                uses booleanAlarmConfig {
                    refine "setSoakSeconds" {
                        default 0;
                    }
                    refine "clearSoakSeconds" {
                        default 60;
                    }
                }
            }

            container raidDiskAlert {
                tailf:info "Minor boolean alarm for /card[slot]/disk[name]/healthy";
                uses booleanAlarmConfig {
                    refine "setSoakSeconds" {
                        default 0;
                    }
                    refine "clearSoakSeconds" {
                        default 60;
                    }
                }
            }
        }

        container control {
            container unknownSaiPktsExceeded {
                tailf:info "Minor rate alarm";
                uses rateAlarmConfig {
                    refine "setThreshold" {
                        default 100000;
                    }
                    refine "clearThreshold" {
                        default 1000;
                    }
                }

                /*  clearThreshold <= setThreshold  */
                must "clearThreshold <= setThreshold" {
                    tailf:dependency '.';
                    error-message "unkownSaiPktsExceeded clearThreshold must be <= setThreshold";
                }
            }

            container activePdpSessionsExceeded {
                tailf:info "Major gauge alarm for /threeGpp/ranapStats/activePdpSessions";
                uses gaugeAlarmConfig {
                    refine "setThreshold" {
                        default 100000;
                    }
                    refine "clearThreshold" {
                        default 90000;
                    }
                }

                /*  clearThreshold <= setThreshold  */
                must "clearThreshold <= setThreshold" {
                    tailf:dependency '.';
                    error-message "activePdpSessionsExceeded clearThreshold must be <= setThreshold";
                }
            }

            container cdsSessionMismatchPktsExceeded {
                tailf:info "Minor rate alarm";
                uses rateAlarmConfig {
                    refine "setThreshold" {
                        default 1000;
                    }
                    refine "clearThreshold" {
                        default 100;
                    }
                }

                /*  clearThreshold <= setThreshold  */
                must "clearThreshold <= setThreshold" {
                    tailf:dependency '.';
                    error-message "cdsSessionMismatchPktsExceeded clearThreshold must be <= setThreshold";
                }
            }

            container threeGppSessionMismatchPktsExceeded {
                tailf:info "Minor rate alarm";
                uses rateAlarmConfig {
                    refine "setThreshold" {
                        default 100000;
                    }
                    refine "clearThreshold" {
                        default 10000;
                    }
                }

                /*  clearThreshold <= setThreshold  */
                must "clearThreshold <= setThreshold" {
                    tailf:dependency '.';
                    error-message "threeGppSessionMismatchPktsExceeded clearThreshold must be <= setThreshold";
                }
            }

            container servicePlaneConnectionDown {
                tailf:info "Critical boolean alarm";
                uses booleanAlarmConfig;
            }

            container managementPlaneConnectionDown {
                tailf:info "Major boolean alarm";
                uses booleanAlarmConfig;
            }

            container onlineChargingConnectionDown {
                tailf:info "Critical boolean alarm";
                uses booleanAlarmConfig;
            }

            container offlineChargingConnectionDown {
                tailf:info "Critical boolean alarm";
                uses booleanAlarmConfig;
            }

            container gspmQueryResponsesDelayed {
                tailf:hidden deprecated;
                uses rateAlarmConfig;
            }

            container chargingQueryResponsesDelayed {
                uses rateAlarmConfig {
                    refine "setThreshold" {
                        default 1;
                    }
                    refine "clearThreshold" {
                        default 0;
                    }
                }

                /*  clearThreshold <= setThreshold  */
                must "clearThreshold <= setThreshold" {
                    tailf:dependency '.';
                    error-message "chargingQueryResponsesDelayed clearThreshold must be <= setThreshold";
                }
            }
            container southPointCodeDown {
                tailf:info "Critical boolean alarm for /threeGpp/path[rnc][sgsn]/status/sSccpSpStatus";
                uses booleanAlarmConfig {
                    refine "setSoakSeconds" {
                        default 0;
                    }
                }
            }

            container northPointCodeDown {
                tailf:info "Critical boolean alarm for /threeGpp/path[rnc][sgsn]/status/nSccpSpStatus";
                uses booleanAlarmConfig {
                    refine "setSoakSeconds" {
                        default 0;
                    }
                }
            }

            container pathStatusTransition {
                tailf:info "Critical boolean alarm for CAE path status Transition";

                uses booleanAlarmConfig {
                    refine "setSoakSeconds" {
                        default 0;
                    }
                }
            }

            container sigtranAssociationDownExceeded {
                tailf:info "Major rate alarm for /threeGpp/path[rnc][sgsn]/sctpStats/numOfAssocDown";
                uses rateAlarmConfig {
                    refine "setThreshold" {
                        default 1;
                    }
                    refine "clearThreshold" {
                        default 0;
                    }
                }

                /*  clearThreshold <= setThreshold  */
                must "clearThreshold <= setThreshold" {
                    tailf:dependency '.';
                    error-message "sigtranAssociationDownExceeded clearThreshold must be <= setThreshold";
                }
            }
        }

        container bearer {
            container ranSectorCongested {
                tailf:info "Major boolean alarm for /threeGpp/sector[nodeB][id]/status/congested";
                uses booleanAlarmConfig {
                    refine "setSoakSeconds" {
                        default 0;
                    }
                    refine "clearSoakSeconds" {
                        default 60;
                    }
                }
            }

            container ranSectorConfigurationError {
                tailf:info "Minor boolean alarm for /threeGpp/sector[nodeB][id]/status/configurationError";
                uses booleanAlarmConfig {
                    refine "setSoakSeconds" {
                        default 0;
                    }
                    refine "clearSoakSeconds" {
                        default 60;
                    }
                }
            }

            container ranNodeBCongested {
                tailf:info "Major boolean alarm for /threeGpp/nodeB[name]/status/congested";
                uses booleanAlarmConfig {
                    refine "setSoakSeconds" {
                        default 0;
                    }
                    refine "clearSoakSeconds" {
                        default 60;
                    }
                }
            }

            container ranNodeBConfigurationError {
                tailf:info "Minor boolean alarm for /threeGpp/nodeB[name]/status/configurationError";
                uses booleanAlarmConfig {
                    refine "setSoakSeconds" {
                        default 0;
                    }
                    refine "clearSoakSeconds" {
                        default 60;
                    }
                }
            }

            container ranBackhaulCongested {
                tailf:info "Major boolean alarm for /threeGpp/backhaul[name]/status/congested";
                uses booleanAlarmConfig {
                    refine "setSoakSeconds" {
                        default 0;
                    }
                    refine "clearSoakSeconds" {
                        default 60;
                    }
                }
            }

            container ranBackhaulConfigurationError {
                tailf:info "Minor boolean alarm for /threeGpp/backhaul[name]/status/configurationError";
                uses booleanAlarmConfig {
                    refine "setSoakSeconds" {
                        default 0;
                    }
                    refine "clearSoakSeconds" {
                        default 60;
                    }
                }
            }

            container activeVideoPacingSessionsExceeded {
                tailf:info "Major gauge alarm";
                uses gaugeAlarmConfig {
                    refine "setThreshold" {
                        default 400;
                    }
                    refine "clearThreshold" {
                        default 350;
                    }
                }

                /*  clearThreshold <= setThreshold  */
                must "clearThreshold <= setThreshold" {
                    tailf:dependency '.';
                    error-message "activeVideoPacingSessionsExceeded clearThreshold must be <= setThreshold";
                }
            }

            container activeHttpProxyTcpConnectionsExceeded {
                tailf:info "Major gauge alarm";
                uses gaugeAlarmConfig {
                    refine "setThreshold" {
                        default 100000;
                    }
                    refine "clearThreshold" {
                        default 80000;
                    }
                }

                /*  clearThreshold <= setThreshold  */
                must "clearThreshold <= setThreshold" {
                    tailf:dependency '.';
                    error-message "activeHttpProxyTcpConnectionsExceeded clearThreshold must be <= setThreshold";
                }
            }

            container httpProxyTcpConnectionFailures {
                tailf:info "Major rate alarm";
                uses rateAlarmConfig {
                    refine "setThreshold" {
                        default 100;
                    }
                    refine "clearThreshold" {
                        default 50;
                    }
                }

                /*  clearThreshold <= setThreshold  */
                must "clearThreshold <= setThreshold" {
                    tailf:dependency '.';
                    error-message "httpProxyTcpConnectionFailures clearThreshold must be <= setThreshold";
                }
            }

            container transitCacheConnectionFailure {
                tailf:info "Major rate alarm";
                uses rateAlarmConfig {
                    refine "setThreshold" {
                        default 100;
                    }
                    refine "clearThreshold" {
                        default 50;
                    }
                }

                /*  clearThreshold <= setThreshold  */
                must "clearThreshold <= setThreshold" {
                    tailf:dependency '.';
                    error-message "transitCacheConnectionFailure clearThreshold must be <= setThreshold";
                }
            }

            container transitCachePrematureClose {
                tailf:info "Major rate alarm";
                uses rateAlarmConfig {
                    refine "setThreshold" {
                        default 100;
                    }
                    refine "clearThreshold" {
                        default 50;
                    }
                }

                /*  clearThreshold <= setThreshold  */
                must "clearThreshold <= setThreshold" {
                    tailf:dependency '.';
                    error-message "transitCachePrematureClose clearThreshold must be <= setThreshold";
                }
            }

            container activeTcpProxyTcpConnectionsExceeded {
                tailf:info "Major gauge alarm";
                uses gaugeAlarmConfig {
                    refine "setThreshold" {
                        default 15000;
                    }
                    refine "clearThreshold" {
                        default 14000;
                    }
                }

                /*  clearThreshold <= setThreshold  */
                must "clearThreshold <= setThreshold" {
                    tailf:dependency '.';
                    error-message "activeTcpProxyTcpConnectionsExceeded clearThreshold must be <= setThreshold";
                }
            }

            container tcpProxyTcpConnectionFailures {
                tailf:info "Major rate alarm";
                uses rateAlarmConfig {
                    refine "setThreshold" {
                        default 10;
                    }
                    refine "clearThreshold" {
                        default 5;
                    }
                }

                /*  clearThreshold <= setThreshold  */
                must "clearThreshold <= setThreshold" {
                    tailf:dependency '.';
                    error-message "tcpProxyConnectionFailures clearThreshold must be <= setThreshold";
                }
            }

            container dnsQueryFailures {
                tailf:info "Major rate alarm";
                uses rateAlarmConfig {
                    refine "setThreshold" {
                        default 30;
                    }
                    refine "clearThreshold" {
                        default 10;
                    }
                }

                /*  clearThreshold <= setThreshold  */
                must "clearThreshold <= setThreshold" {
                    tailf:dependency '.';
                    error-message "dnsQueryFailures clearThreshold must be <= setThreshold";
                }
            }

            container domainConnectionFailures {
                tailf:info "Major rate alarm";
                uses rateAlarmConfig {
                    refine "setThreshold" {
                        default 100;
                    }
                    refine "clearThreshold" {
                        default 10;
                    }
                }

                /*  clearThreshold <= setThreshold  */
                must "clearThreshold <= setThreshold" {
                    tailf:dependency '.';
                    error-message "domainConnectionFailures clearThreshold must be <= setThreshold";
                }
            }

            container unsolicitedDnsResponsesExceeded {
                tailf:info "Minor rate alarm";
                uses rateAlarmConfig {
                    refine "setThreshold" {
                        default 30;
                    }
                    refine "clearThreshold" {
                        default 10;
                    }
                }

                /*  clearThreshold <= setThreshold  */
                must "clearThreshold <= setThreshold" {
                    tailf:dependency '.';
                    error-message "unsolicitedDnsResponsesExceeded clearThreshold must be <= setThreshold";
                }
            }
        }

        container hardware {
            container eccErrorsExceeded {
                tailf:info "Minor rate alarm";
                uses rateAlarmConfig {
                    refine "setThreshold" {
                        default 1;
                    }
                    refine "clearThreshold" {
                        default 0;
                    }
                }

                /*  clearThreshold <= setThreshold  */
                must "clearThreshold <= setThreshold" {
                    tailf:dependency '.';
                    error-message "eccErrorsExceeded clearThreshold must be <= setThreshold";
                }
            }
        }

        container application {
            container httpProxyCpuWarning {
                tailf:info "Minor gauge alarm for /node/application[slot][service='httpProxy'][component='httpProxy']";
                uses gaugeAlarmConfig {
                    refine "setThreshold" {
                        tailf:info %;
                        default 80;
                    }
                    refine "clearThreshold" {
                        tailf:info %;
                        default 70;
                    }
                    refine "setSoakSeconds" {
                        default 30;
                    }
                    refine "clearSoakSeconds" {
                        default 15;
                    }
                }

                /*  clearThreshold <= setThreshold  */
                must "clearThreshold <= setThreshold" {
                    tailf:dependency '.';
                    error-message "httpProxyCpuWarning clearThreshold must be <= setThreshold";
                }
            }

            container httpProxyCpu {
                tailf:info "Major gauge alarm for /node/application[slot][service='httpProxy'][component='httpProxy']";
                uses gaugeAlarmConfig {
                    refine "setThreshold" {
                        tailf:info %;
                        default 100;
                    }
                    refine "clearThreshold" {
                        tailf:info %;
                        default 90;
                    }
                    refine "setSoakSeconds" {
                        default 60;
                    }
                    refine "clearSoakSeconds" {
                        default 30;
                    }
                }

                /*  clearThreshold <= setThreshold  */
                must "clearThreshold <= setThreshold" {
                    tailf:dependency '.';
                    error-message "httpProxyCpu clearThreshold must be <= setThreshold";
                }
            }

            /*  httpProxyCpuWarning thresholds <= httpProxyCpu thresholds  */
            must "httpProxyCpuWarning/setThreshold <= httpProxyCpu/setThreshold" {
                tailf:dependency 'httpProxyCpuWarning/setThreshold';
                tailf:dependency 'httpProxyCpu/setThreshold';
                error-message "httpProxyCpuWarning/setThreshold must be <= httpProxyCpu/setThreshold";
            }
            must "httpProxyCpuWarning/clearThreshold <= httpProxyCpu/clearThreshold" {
                tailf:dependency 'httpProxyCpuWarning/clearThreshold';
                tailf:dependency 'httpProxyCpu/clearThreshold';
                error-message "httpProxyCpuWarning/clearThreshold must be <= httpProxyCpu/clearThreshold";
            }

            container httpProxyMemoryWarning {
                tailf:info "Minor gauge alarm for /node/application[slot][service='httpProxy'][component='httpProxy']";
                uses gaugeAlarmConfig {
                    refine "setThreshold" {
                        tailf:info "physical utilization in KB";
                        default 2097152;
                    }
                    refine "clearThreshold" {
                        tailf:info "physical utilization in KB";
                        default 1572864;
                    }
                    refine "setSoakSeconds" {
                        default 30;
                    }
                    refine "clearSoakSeconds" {
                        default 15;
                    }
                }

                /*  clearThreshold <= setThreshold  */
                must "clearThreshold <= setThreshold" {
                    tailf:dependency '.';
                    error-message "httpProxyMemoryWarning clearThreshold must be <= setThreshold";
                }
            }

            container httpProxyMemory {
                tailf:info "Major gauge alarm for /node/application[slot][service='httpProxy'][component='httpProxy']";
                uses gaugeAlarmConfig {
                    refine "setThreshold" {
                        tailf:info "physical utilization in KB";
                        default 3145728;
                    }
                    refine "clearThreshold" {
                        tailf:info "physical utilization in KB";
                        default 2621440;
                    }
                    refine "setSoakSeconds" {
                        default 60;
                    }
                    refine "clearSoakSeconds" {
                        default 30;
                    }
                }

                /*  clearThreshold <= setThreshold  */
                must "clearThreshold <= setThreshold" {
                    tailf:dependency '.';
                    error-message "httpProxyMemory clearThreshold must be <= setThreshold";
                }
            }

            /*  httpProxyMemoryWarning thresholds <= httpProxyMemory thresholds  */
            must "httpProxyMemoryWarning/setThreshold <= httpProxyMemory/setThreshold" {
                tailf:dependency 'httpProxyMemoryWarning/setThreshold';
                tailf:dependency 'httpProxyMemory/setThreshold';
                error-message "httpProxyMemoryWarning/setThreshold must be <= httpProxyMemory/setThreshold";
            }
            must "httpProxyMemoryWarning/clearThreshold <= httpProxyMemory/clearThreshold" {
                tailf:dependency 'httpProxyMemoryWarning/clearThreshold';
                tailf:dependency 'httpProxyMemory/clearThreshold';
                error-message "httpProxyMemoryWarning/clearThreshold must be <= httpProxyMemory/clearThreshold";
            }
        }
    }

    /* alarm notification */
    notification alarmNotification {
        leaf category {
            type alarmCategoryType;
            mandatory true;
        }
        leaf alarmId {
            type alarmIdType;
            mandatory true;
        }
        leaf xpath {
            type string;
            mandatory true;
        }
        leaf severity {
            type alarmSeverityType;
            mandatory true;
        }
        leaf condition {
            type alarmConditionType;
            mandatory true;
        }
        leaf value {
            type string;
            mandatory true;
        }
        leaf extra {
            type string;
            mandatory true;
        }
        leaf seqNum {
            type uint32;
            mandatory true;
        }
    }

    /*  config commit notification */
    notification configNotification {
        leaf configOpCode {
            type configOpCode;
            mandatory true;
        }
        leaf xpath {
            type string;
            mandatory true;
        }
        leaf commitSeqNum {
            type uint32;
            mandatory true;
        }
    }
}
