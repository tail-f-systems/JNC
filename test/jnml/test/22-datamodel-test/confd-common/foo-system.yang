module foo-system {
    namespace "http://foo.net/ns/foo-system";
    prefix foo-system;

    import ietf-yang-types {
        prefix yang;
    }

    import tailf-common {
        prefix tailf;
    }

    include foo-system-types;
    include foo-system-node;
    include foo-system-card;
    include foo-system-ethernet;
    include foo-system-ip;

    organization "Foo Networks, Inc.";
    description  "Managed objects for alarms.";

    // add new revision statements here

    revision 2011-01-06 {
        description "Conversion from confspec.";
    }


    container system {
        container location {
            leaf organization {
                type string;
                default "Foo Networks Inc.";
            }
            leaf chassis {
                type string;
                default "Foo CAE Release 1.0";
            }
            leaf streetAddress {
                type string;
                default "One Monarch Drive";
            }
            leaf city {
                type string;
                default Littleton;
            }
            leaf state {
                type string;
                default MA;
            }
            leaf zipCode {
                type string;
                default 01460;
            }
            leaf gpsLocation {
                type string;
                default "Foo CAE Release 1.0";
            }
        }

        container contact {
            leaf contactInfo {
                type string;
                default "Foo Networks Inc.";
            }
            leaf phoneNumber1 {
                type string;
                default +919785401600;
            }
            leaf phoneNumber2 {
                type string;
                default +918067343200;
            }
            leaf contactDetails {
                type string;
                default "One Monarch Drive, Littleton, MA, 01460";
            }
        }

        container operationalState {
            config false;
            tailf:hidden debug;

            tailf:cdb-oper {
                tailf:persistent true;
            }

            leaf alarmSeqNum {
                type uint32;
                default 0;
            }
            leaf commitSeqNum {
                type uint32;
                default 0;
            }
        }

        container version {
            config false;
            tailf:cdb-oper;

            leaf primaryBootFirmware {
                type string;
            }
            leaf secondaryBootFirmware {
                type string;
            }
            leaf currentSoftwareVersion {
                type string;
            }
            leaf backupSoftwareVersion {
                type string;
            }
        }

        container information {
            config false;
            tailf:cdb-oper;

            leaf modelNumber {
                type string;
            }
            leaf partNumber {
                type string;
            }
            leaf serialNumber {
                type string;
            }
            leaf assemblyDate {
                type yang:date-and-time;
            }
        }
    }
}
