module foo-trace {
    namespace "http://foo.net/ns/foo-trace";
    prefix foo-trace;

    import ietf-inet-types {
        prefix inet;
    }
    import tailf-common {
        prefix tailf;
    }

    include foo-trace-types;

    organization "Foo Networks, Inc.";
    description  "Managed objects for system trace.";

    // add new revision statements here

    revision 2011-01-06 {
        description "Conversion from confspec.";
    }


    list trace {
        key "application slot";
        tailf:info "Application debug trace configuration";

        /*  cross-check slot against application  */

        leaf application {
            type appNameType;
        }
        leaf slot {
            type slotType;
        }
        leaf level {
            type traceLevelType;
            default error;
        }
        leaf fileSize {
            type uint32;
            default 10240;
        }
        leaf fileCount {
            type uint32;
            default 10;
        }
        leaf subComponents {
            type subComponentsType;
            default "";
        }
    }

    container systemTrace {
        container sessionContext {
            leaf ueIpAddress {
                type inet:ipv4-address;
                default 0.0.0.0;
            }
            leaf sessionId {
                type uint32;
                default 0;
            }
            leaf msisdn {
                type string;
                default "";
            }
        }

        container control {
            leaf level {
                type traceLevelType;
                default warning;
            }
            leaf filePrefix {
                type string;
                default cae-system;
            }
            leaf fileSize {
                type uint32;
                default 10000;
            }
            leaf fileCount {
                type uint32;
                default 1;
            }
        }
    }
}
