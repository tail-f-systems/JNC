submodule foo-system-ip {
    belongs-to foo-system {
        prefix foo-system;
    }

    import tailf-common {
        prefix tailf;
    }

    import ietf-inet-types {
        prefix inet;
    }

    import foo-alarm {
        prefix foo-alarm;
    }

    include foo-system-types;
    include foo-system-ethernet;

    // add new revision statements here

    revision 2011-01-06 {
        description "Conversion from confspec.";
    }


    container ip {
        list interface {
            key name;

            /*  application-specific validation  */

            leaf name {
                type nameType;
            }
            leaf adminState {
                type adminOperType;
                default up;
            }

            container binding {
                container ethernet {
                    list port {
                        key "slot port";
                        max-elements 1;

                        leaf slot {
                            type leafref {
                                path "/ethernet/port/slot";
                            }
                        }
                        leaf port {
                            type leafref {
                                path "/ethernet/port/port";
                            }
                        }

                        /*  ensure that the port is not used by another /ip/interface  */
                        must "count(.[slot=current()/slot][port=current()/port]) <= 1" {
                            tailf:dependency '.';
                            error-message "port already has an interface";
                        }

                        /*  ensure that the port is not part of a lag  */
                        must "count(/ethernet/lag/port[slot=current()/slot][port=current()/port]) = 0" {
                            tailf:dependency '.';
                            tailf:dependency '/ethernet/lag/port';
                            error-message "port is in use by a LAG";
                        }
                    }

                    list portVlan {
                        key "slot port vid";
                        max-elements 1;

                        leaf slot {
                            type leafref {
                                path "../../../../../../ethernet/port/slot";
                            }
                        }
                        leaf port {
                            type leafref {
                                path "../../../../../../ethernet/port/port";
                            }
                        }
                        leaf vid {
                            type leafref {
                                path "../../../../../../ethernet/port/vlan/vid";
                            }
                        }

                        /*  ensure that the portVlan is not used by another /ip/interface  */
                        must "count(.[slot=current()/slot][port=current()/port][vid=current()/vid]) <= 1" {
                            tailf:dependency '.';
                            error-message "VLAN already has an interface";
                        }

                        /*  ensure that the port is not part of a lag  */
                        must "count(/ethernet/lag/port[slot=current()/slot][port=current()/port]) = 0" {
                            tailf:dependency '.';
                            tailf:dependency '/ethernet/lag/port'; 
                            error-message "port is in use by a LAG";
                        }
                    }

                    list lag {
                        key name;
                        max-elements 1;

                        leaf name {
                            type leafref {
                                path "/ethernet/lag/name";
                            }
                        }

                        /*  ensure that the lag is not used by another /ip/interface  */
                        must "count(.[name=current()/name]) <= 1" {
                            tailf:dependency '.';
                            error-message "LAG already has an interface";
                        }
                    }

                    list lagVlan {
                        key "name vid";
                        max-elements 1;

                        leaf name {
                            type leafref {
                                path "/ethernet/lag/name";
                            }
                        }
                        leaf vid {
                            type leafref {
                                path "/ethernet/lag/vlan/vid";
                            }
                        }

                        /*  ensure that the lagVlan is not used by another /ip/interface  */
                        must "count(.[name=current()/name][vid=current()/vid]) <= 1" {
                            tailf:dependency '.';
                            error-message "VLAN already has an interface";
                        }
                    }
                }

                /*  ensure that exactly 1 binding has been made  */
                must "(count(ethernet/port) + count(ethernet/portVlan) + count(ethernet/lag) + count(ethernet/lagVlan)) = 1" {
                    tailf:dependency '.';
                    error-message "must have exactly 1 binding";
                }
            }

            container status {
                config false;
                tailf:cdb-oper;

                leaf operStatus {
                    type adminOperType;
                }
                leaf txUtilization {
                    type uint8;
                }
                leaf rxUtilization {
                    type uint8;
                }
                leaf utilization {
                    type uint8;
                    tailf:info " utilization is max(rxUtilization,txUtilization) ";
                }
            }

            container counters {
                config false;
                tailf:cdb-oper;

                leaf rxBytes {
                    type uint64;
                }
                leaf rxPkts {
                    type uint64;
                }
                leaf rxErrors {
                    type uint64;
                }
                leaf rxDropped {
                    type uint64;
                }
                leaf rxOverrun {
                    type uint64;
                }
                leaf rxMcast {
                    type uint64;
                }
                leaf txBytes {
                    type uint64;
                }
                leaf txPkts {
                    type uint64;
                }
                leaf txErrors {
                    type uint64;
                }
                leaf txDropped {
                    type uint64;
                }
                leaf txCarrier {
                    type uint64;
                }
                leaf txCollsns {
                    type uint64;
                }
            }

            container alarm {
                container linkDown {
                    presence "alarm override";
                    uses foo-alarm:booleanAlarmConfig;
                }
                container interfaceUtilizationWarning {
                    presence "alarm override";
                    uses foo-alarm:gaugeAlarmConfig;
                }
                container interfaceUtilization {
                    presence "alarm override";
                    uses foo-alarm:gaugeAlarmConfig;
                }
                container interfaceRxPps {
                    presence "alarm override";
                    uses foo-alarm:rateAlarmConfig;
                }
                container interfaceTxPps {
                    presence "alarm override";
                    uses foo-alarm:rateAlarmConfig;
                }
                container interfaceLowRxPps {
                    presence "alarm override";
                    uses foo-alarm:rateAlarmConfig;
                }
                container interfaceLowTxPps {
                    presence "alarm override";
                    uses foo-alarm:rateAlarmConfig;
                }
                container interfaceRxPktDropWarning {
                    presence "alarm override";
                    uses foo-alarm:rateAlarmConfig;
                }
                container interfaceRxPktDrop {
                    presence "alarm override";
                    uses foo-alarm:rateAlarmConfig;
                }
                container interfaceTxPktDropWarning {
                    presence "alarm override";
                    uses foo-alarm:rateAlarmConfig;
                }
                container interfaceTxPktDrop {
                    presence "alarm override";
                    uses foo-alarm:rateAlarmConfig;
                }
            }
        }

        list ifaddr {
            key addr;

            /*  application-specific validation  */

            leaf addr {
                type inet:ipv4-address;
            }
            leaf mask {
                type inet:ipv4-address;
                mandatory true;
            }
            leaf isHaVirtual {
                type boolean;
                default false;
                tailf:info "Whether this ifaddr fails over in an HA switchover";
            }
        }

        list route {
            key prefix;

            /*  application-specific validation  */

            leaf prefix {
                type inet:ipv4-prefix;
            }
            leaf metric {
                type uint16;
                default 100;
            }
            leaf interface {
                type leafref {
                    path "../../interface/name";
                }
            }
            leaf gateway {
                type inet:ipv4-address;
            }
        }
    }
}
