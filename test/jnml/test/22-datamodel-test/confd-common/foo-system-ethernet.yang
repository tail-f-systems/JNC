submodule foo-system-ethernet {
    belongs-to foo-system {
        prefix foo-systme;
    }

    import tailf-common {
        prefix tailf;
    }

    include foo-system-types;
    include foo-system-card;

    // add new revision statements here

    revision 2011-01-06 {
        description "Conversion from confspec.";
    }


    /*  ethernet  */
    container ethernet {
        /*  port  */
        list port {
            key "slot port";

            leaf slot {
                type leafref {
                    path "/card/slot";
                }
            }
            leaf port {
                type uint16;
            }
            leaf adminState {
                type adminOperType;
                default up;
            }

            /*  vlan  */
            list vlan {
                key vid;
                tailf:info "valid VLANs on this (non-LAG) port";

                leaf vid {
                    type vidType;
                }

                /*  ensure that the port is not part of a lag  */
                must "count(/ethernet/lag/port[slot=current()/../slot][port=current()/../port]) = 0" {
                    tailf:dependency '.';
                    tailf:dependency '/ethernet/lag/port';
                    error-message "port is in use by a LAG";
                }
            }

            container status {
                config false;
                tailf:cdb-oper;

                leaf operStatus {
                    type adminOperType;
                }
            }
        }

        /*  lag  */
        list lag {
            key name;
            tailf:info "Link Aggregation Group is a logical grouping of Ethernet ports";

            leaf name {
                type nameType;
            }
            leaf adminState {
                type adminOperType;
                default up;
            }
            leaf minActiveLinks {
                type uint16;
                default 1;
            }
            leaf maxActiveLinks {
                type uint16;
                default 1;
            }

            /*  port  */
            list port {
                key "slot port";
                tailf:info "member ports";

                leaf slot {
                    type leafref {
                        path "../../../port/slot";
                    }
                }
                leaf port {
                    type leafref {
                        path "../../../port/port";
                    }
                }

                /*  ensure that the port has no interfaces  */
                must "count(/ip/interface/binding/ethernet/port[slot=current()/slot][port=current()/port]) = 0" {
                    tailf:dependency '.';
                    tailf:dependency '/ip/interface/binding/ethernet/port';
                    error-message "port has an ip interface";
                }
            }

            /*  vlan  */
            list vlan {
                key vid;
                tailf:info "valid VLANs on this LAG";

                leaf vid {
                    type vidType;
                }
            }

            container status {
                config false;
                tailf:cdb-oper;

                leaf numActiveLinks {
                    type uint16;
                }
                leaf operStatus {
                    type adminOperType;
                }
            }
        }
    }
}
