submodule foo-system-card {
    belongs-to foo-system {
        prefix foo-system;
    }

    import tailf-common {
        prefix tailf;
    }

    include foo-system-types;

    // add new revision statements here

    revision 2011-01-06 {
        description "Conversion from confspec.";
    }


    /*  card  */
    list card {
        key slot;

        /*  application-specific validation  */

        leaf slot {
            type slotType;
        }
        leaf cardType {
            type cardTypeType;
            mandatory true;
        }
        leaf adminState {
            type adminOperType;
            default down;
            tailf:hidden deprecated;
        }

        container status {
            config false;
            tailf:cdb-oper;

            leaf operStatus {
                type adminOperType;
            }
            leaf temperature {
                type int8;
                tailf:info "degrees Celcius";
            }
            leaf memoryUtilization {
                type uint8;
            }
            leaf cpuUtilization {
                type uint8;
            }
        }

        /*  cpu  */
        list cpu {
            key id;
            config false;
            tailf:cdb-oper;

            leaf id {
                type uint16;
            }
            leaf utilization {
                type uint8;
            }
        }

        /*  power supply  */
        list powerSupply {
            key id;
            config false;
            tailf:cdb-oper;

            leaf id {
                type uint16;
            }
            leaf present {
                type boolean;
            }
            leaf operStatus {
                type adminOperType;
            }
        }

        /*  fan  */
        list fan {
            key id;
            config false;
            tailf:cdb-oper;

            leaf id {
                type uint16;
            }
            leaf present {
                type boolean;
            }
            leaf operStatus {
                type adminOperType;
            }
        }

        /*  disk  */
        list disk {
            key name;
            config false;
            tailf:cdb-oper;

            leaf name {
                type nameType;
            }
            leaf healthy {
                type boolean;
            }

            list device {
                key id;
                tailf:cdb-oper;

                leaf id {
                    type uint16;
                }
                leaf present {
                    type boolean;
                }
                leaf healthy {
                    type boolean;
                }
            }

            list partition {
                key name;
                tailf:cdb-oper;

                leaf name {
                    type nameType;
                }
                leaf mounted {
                    type boolean;
                }
                leaf utilization {
                    type uint8;
                }
            }
        }

        /* HA Applications state  */
        list appstate {
            key "service component";
            config false;
            tailf:cdb-oper;

            leaf service {
                type nameType;
            }
            leaf component {
                type nameType;
            }
            leaf haState {
                type haStateType;
            }
            leaf appState {
                type applicationStateType;
            }
            leaf forwarding {
                type enableDisableType;
            }
            leaf peerState {
                type peerStateType;
            }
            leaf startTime {
                type string;
            }
        }

        /* HA commands  */
        container ha {
            config false;
            tailf:cdb-oper;

            tailf:action enableSlot {
                tailf:actionpoint cardHaApp;
                tailf:confirm-text "Do you want to proceed?";
                input {
                }
                output {
                    leaf reply {
                        type string;
                        mandatory true;
                    }
                }
            }

            tailf:action enableForwarding {
                tailf:actionpoint cardHaApp;
                tailf:confirm-text "Do you want to proceed?";
                input {
                }
                output {
                    leaf reply {
                        type string;
                        mandatory true;
                    }
                }
            }

            tailf:action disableForwarding {
                tailf:actionpoint cardHaApp;
                tailf:confirm-text "Do you want to proceed?";
                input {
                }
                output {
                    leaf reply {
                        type string;
                        mandatory true;
                    }
                }
            }

            tailf:action switchOver {
                tailf:actionpoint cardHaSaf;
                tailf:confirm-text "Do you want to proceed?";
                input {
                    leaf service {
                        type string;
                        mandatory true;
                    }
                }
                output {
                    leaf reply {
                        type string;
                        mandatory true;
                    }
                }
            }

            tailf:action enablePeerNode {
                tailf:actionpoint cardHaSaf;
                tailf:confirm-text "Do you want to proceed?";
                input {
                }
                output {
                    leaf reply {
                        type string;
                        mandatory true;
                    }
                }
            }

            tailf:action disableNode {
                tailf:actionpoint cardHaSaf;
                tailf:confirm-text "Do you want to proceed?";
                input {
                }
                output {
                    leaf reply {
                        type string;
                        mandatory true;
                    }
                }
            }

            tailf:action enableNode {
                tailf:actionpoint cardHaSaf;
                tailf:confirm-text "Do you want to proceed?";
                input {
                }
                output {
                    leaf reply {
                        type string;
                        mandatory true;
                    }
                }
            }

            tailf:action enable {
                tailf:actionpoint cardHaSaf;
                tailf:confirm-text "Do you want to proceed?";
                input {
                    leaf service {
                        type string;
                        mandatory true;
                    }
                }
                output {
                    leaf reply {
                        type string;
                        mandatory true;
                    }
                }
            }

            tailf:action disable {
                tailf:actionpoint cardHaSaf;
                tailf:confirm-text "Do you want to proceed?";
                input {
                    leaf service {
                        type string;
                        mandatory true;
                    }
                }
                output {
                    leaf reply {
                        type string;
                        mandatory true;
                    }
                }
            }

            tailf:action restart {
                tailf:actionpoint cardHaSaf;
                tailf:confirm-text "Do you want to proceed?";
                input {
                    leaf service {
                        type string;
                        mandatory true;
                    }
                }
                output {
                    leaf reply {
                        type string;
                        mandatory true;
                    }
                }
            }
        }
    }
}
