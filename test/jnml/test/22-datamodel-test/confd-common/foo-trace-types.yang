submodule foo-trace-types {
    belongs-to foo-trace {
        prefix foo-trace;
    }

    // add new revision statements here

    revision 2011-01-06 {
        description "Conversion from confspec.";
    }


    typedef traceLevelType {
        type enumeration {
            enum debug1;
            enum debug;
            enum info;
            enum warning;
            enum error;
            enum none;
        }
    }

    typedef slotType {
        type uint16 {
            range "1 .. 12";
        }
    }

    typedef appNameType {
        type enumeration {
            /*  CAE-specific  */
            enum systemMgr;
            enum alarmMgr;
            enum ranap;
            enum sccp;
            enum httpProxy;
            enum gtpProxy;
            enum atmAgent;
            enum cspm;
            enum dnsProxy;
            enum tcpProxy;
            enum statsAggr;
            enum tproxyMgr;
            enum bwMgr;
            enum hbm;
            enum stackapp;
            enum netmon;
            enum sctpmon;
            enum sscopmon;
            enum resourceAgent;
            enum resourceMgr;
            enum safBroker;
            enum arpMgr;
            enum ccm;
            enum ocsSim;
            enum a11sim;
            enum htCacheClean;
            /*  SPX-specific  */
            enum topologyManager;
            enum radiusServer;
            enum ldap;
            enum usm;
            enum scm;
            enum diameter;
            enum sdbi;
        }
    }

    typedef subComponentsType {
        type bits {
            bit all { position 30; } 
            bit alarmLib { position 29; } 
            bit commonLib { position 28; } 
            bit policyLib { position 27; } 
            bit confdLib { position 26; } 
            bit ipc { position 25; } 
            bit sccpLib { position 24; } 
        }
    }
}
