submodule foo-alarm-types {
    belongs-to foo-alarm {
        prefix foo-alarm;
    }

    // add new revision statements here

    revision 2011-01-06 {
        description "Conversion from confspec.";
    }


    typedef alarmCategoryType {
        // only add to the end to maintain synchronization with MOVIK-TRAP-MIB
        type enumeration {
            enum invalid;
            enum system;
            enum chassis;
            enum control;
            enum bearer;
            enum hardware;
            enum application;
        }
    }

    typedef alarmSeverityType {
        // only add to the end to maintain synchronization with MOVIK-TRAP-MIB
        type enumeration {
            enum invalid;
            enum critical;
            enum major;
            enum minor;
            enum informational;
        }
    }

    typedef alarmConditionType {
        // only add to the end to maintain synchronization with MOVIK-TRAP-MIB
        type enumeration {
            enum invalid;
            enum set;
            enum clear;
            enum event;
        }
    }

    typedef alarmIdType {
        // only add to the end to maintain synchronization with MOVIK-TRAP-MIB
        type enumeration {
            enum invalid;                               // 0
            enum coldStart;
            enum warmStart;
            enum internalCommsFailure;
            enum linkDown;
            enum atmControllerDown;
            enum atmPortDown;
            enum atmPortUtilization;
            enum atmPortUtilizationWarning;
            enum applicationFailure;
            enum watchdogFailure;                       // 10
            enum memoryUtilizationWarning;
            enum memoryUtilization;
            enum cpuUtilizationWarning;
            enum cpuUtilization;
            enum diskUtilizationWarning;
            enum diskUtilization;
            enum networkUtilizationWarning;
            enum networkUtilization;
            enum interfaceUtilizationWarning;
            enum interfaceUtilization;                  // 20
            enum interfaceRxPps;
            enum interfaceTxPps;
            enum interfaceLowRxPps;
            enum interfaceLowTxPps;
            enum interfaceRxPktDropWarning;
            enum interfaceRxPktDrop;
            enum interfaceTxPktDrop;
            enum interfaceTxPktDropWarning;
            enum networkRxPpsWarning;
            enum networkRxPps;                          // 30
            enum networkTxPpsWarning;
            enum networkTxPps;
            enum networkLowRxPps;
            enum networkLowTxPps;
            enum hddTransactionRateWarning;
            enum hddTransactionRate;
            enum ssdReadTransactionRateWarning;
            enum ssdReadTransactionRate;
            enum ssdWriteTransactionRateWarning;
            enum ssdWriteTransactionRate;               // 40
            enum obsBypassActive;
            enum resourceControl;
            enum haTransition;
            enum temperatureLow;
            enum temperatureHighWarning;
            enum temperatureHigh;
            enum powerSupplyRemoved;
            enum powerSupplyFailed;
            enum fanRemoved;
            enum fanFailed;                             // 50
            enum diskRemoved;
            enum diskFailed;
            enum raidDiskAlert;
            enum obsPowerFailure;
            enum obsSwitchFailure;
            enum obsDown;
            enum unknownSaiPktsExceeded;
            enum activePdpSessionsExceeded;
            enum cdsSessionMismatchPktsExceeded;
            enum threeGppSessionMismatchPktsExceeded;   // 60
            enum servicePlaneConnectionDown;
            enum managementPlaneConnectionDown;
            enum onlineChargingConnectionDown;
            enum offlineChargingConnectionDown;
            enum gspmQueryResponsesDelayed;
            enum chargingQueryResponsesDelayed;
            enum southPointCodeDown;
            enum northPointCodeDown;
            enum pathStatusTransition;
            enum sigtranAssociationDownExceeded;        // 70
            enum sigtranAssociationEvent;
            enum ranSectorCongested;
            enum ranSectorConfigurationError;
            enum ranNodeBCongested;
            enum ranNodeBConfigurationError;
            enum ranBackhaulCongested;
            enum ranBackhaulConfigurationError;
            enum activeVideoPacingSessionsExceeded;
            enum activeHttpProxyTcpConnectionsExceeded;
            enum httpProxyTcpConnectionFailures;        // 80
            enum transitCacheConnectionFailure;
            enum transitCachePrematureClose;
            enum activeTcpProxyTcpConnectionsExceeded;
            enum tcpProxyTcpConnectionFailures;
            enum dnsQueryFailures;
            enum domainConnectionFailures;
            enum unsolictedDnsResponsesExceeded;
            enum eccErrorsExceeded;
            enum httpProxyCpuWarning;
            enum httpProxyCpu;                          // 90
            enum httpProxyMemoryWarning;
            enum httpProxyMemory;
        }
    }

    typedef configOpCode {
        type enumeration {
            enum create;
            enum delete;
            enum modify;
        }
    }

    typedef alarmPeriodSecondsType {
        type uint32 {
            range "15 .. max";
        }
    }

    grouping booleanAlarmConfig {
        leaf enabled {
            type boolean;
            default true;
        }
        leaf setSoakSeconds {
            type uint32;
            default 10;
        }
        leaf clearSoakSeconds {
            type uint32;
            default 10;
        }
    }

    grouping gaugeAlarmConfig {
        leaf enabled {
            type boolean;
            default true;
        }
        leaf setThreshold {
            type int32;
            default 0;
        }
        leaf clearThreshold {
            type int32;
            default 0;
        }
        leaf setSoakSeconds {
            type uint32;
            default 10;
        }
        leaf clearSoakSeconds {
            type uint32;
            default 10;
        }
    }

    grouping rateAlarmConfig {
        leaf enabled {
            type boolean;
            default true;
        }
        leaf setThreshold {
            type uint64;
            default 0;
        }
        leaf clearThreshold {
            type uint64;
            default 0;
        }
        leaf periodSeconds {
            type uint32;
            default 60;
        }
        leaf eventBurst {
            type uint32;
            default 0;
        }
        leaf eventPeriodSeconds {
            type uint32;
            default 0;
        }
    }
}
