submodule foo-a11sim-types {
    belongs-to foo-a11sim {
        prefix foo-a11sim;
    }

    import tailf-common {
        prefix tailf;
    }

    // add new revision statements here

    revision 2011-01-06 {
        description "Conversion from confspec.";
    }


    typedef loadBalancingMethodType {
        type enumeration {
            enum roundRobin;
            enum stickyInterface1;
            enum stickyInterface2;
            enum stickyInterface3;
            enum stickyInterface4;
            enum stickyInterface5;
            enum stickyInterface6;
        }
    }
    typedef reqProcessingPolicy {
        type enumeration {
            enum accept;
            enum discard;
            enum acceptWithDelay;
            enum acceptWithInvalidId;
            enum rejectWithError;
        }
    }

    grouping sessionStatisticsType {
        leaf sessionsEstabslihed {
            type decimal64 {
                fraction-digits 2;
            }
        }
        leaf sessionsEstablishedButNoUserIpFromIPCP {
            type decimal64 {
                fraction-digits 2;
            }
        }
        leaf sessionsEstablishedWithoutImsi {
            type decimal64 {
                fraction-digits 2;
            }
        }
        leaf sessionsEstablishedWithoutEsn {
            type decimal64 {
                fraction-digits 2;
            }
        }
        leaf sessionsEstablishedWithoutBsid {
            type decimal64 {
                fraction-digits 2;
            }
        }
        leaf sessionsEstablishedWithoutCellid {
            type decimal64 {
                fraction-digits 2;
            }
        }
        leaf sessionsDeletedTotal {
            type decimal64 {
                fraction-digits 2;
            }
        }
        leaf sessionsDeletedWithRegUpdateFirst {
            type decimal64 {
                fraction-digits 2;
            }
        }
        leaf sessionsDeletedWithPppTerminationFirst {
            type decimal64 {
                fraction-digits 2;
            }
        }
        leaf sessionsDeletedDueToAge {
            type decimal64 {
                fraction-digits 2;
            }
        }
    }

    grouping messageStatisticsType {
        container a11Registration {
            tailf:info "A11 Registration Request message statistics";
            leaf ReqInitial {
                type decimal64 {
                    fraction-digits 2;
                }
            }
            leaf ReqReRegistration {
                type decimal64 {
                    fraction-digits 2;
                }
            }
            leaf ReqUpdate {
                type decimal64 {
                    fraction-digits 2;
                }
            }
            leaf ReqWithActiveStart {
                type decimal64 {
                    fraction-digits 2;
                }
            }
            leaf ReqWithActiveStop {
                type decimal64 {
                    fraction-digits 2;
                }
            }
            leaf ReqTerminate {
                type decimal64 {
                    fraction-digits 2;
                }
            }
            leaf ReqParseFail {
                type decimal64 {
                    fraction-digits 2;
                }
            }
            leaf ReplySuccess {
                type decimal64 {
                    fraction-digits 2;
                }
            }
            leaf ReplyFailReasonUnspecified {
                type decimal64 {
                    fraction-digits 2;
                }
            }
            leaf ReplyFailAdminProhibited {
                type decimal64 {
                    fraction-digits 2;
                }
            }
            leaf ReplyFailInsufficientResources {
                type decimal64 {
                    fraction-digits 2;
                }
            }
            leaf ReplyFailAuthFail {
                type decimal64 {
                    fraction-digits 2;
                }
            }
            leaf ReplyFailIdMismatch {
                type decimal64 {
                    fraction-digits 2;
                }
            }
            leaf ReplyFailMalformed {
                type decimal64 {
                    fraction-digits 2;
                }
            }
            leaf ReplyFailReverseTunnelUnavailable {
                type decimal64 {
                    fraction-digits 2;
                }
            }
            leaf ReplyFailReverseTunnelTBitNotSet {
                type decimal64 {
                    fraction-digits 2;
                }
            }
            leaf ReplyFailUnsupportedVendorId {
                type decimal64 {
                    fraction-digits 2;
                }
            }
            leaf ReplyFailUknownPdsn {
                type decimal64 {
                    fraction-digits 2;
                }
            }
            leaf ReplyFailOther {
                type decimal64 {
                    fraction-digits 2;
                }
            }
            leaf ReplyParseFail {
                type decimal64 {
                    fraction-digits 2;
                }
            }
        }

        container a11RegUpdate {
            tailf:info "A11 Registration Update message statistics";
            leaf ReqTotal {
                type decimal64 {
                    fraction-digits 2;
                }
            }
            leaf ReqParseFail {
                type decimal64 {
                    fraction-digits 2;
                }
            }
            leaf AckAccepted {
                type decimal64 {
                    fraction-digits 2;
                }
            }
            leaf AckFailReasonUnspecified {
                type decimal64 {
                    fraction-digits 2;
                }
            }
            leaf AckFailAdminProhibited {
                type decimal64 {
                    fraction-digits 2;
                }
            }
            leaf AckFailAuthFail {
                type decimal64 {
                    fraction-digits 2;
                }
            }
            leaf AckFailIdMismatch {
                type decimal64 {
                    fraction-digits 2;
                }
            }
            leaf AckFailMalformed {
                type decimal64 {
                    fraction-digits 2;
                }
            }
            leaf AckFailOther {
                type decimal64 {
                    fraction-digits 2;
                }
            }
            leaf AckParseFail {
                type decimal64 {
                    fraction-digits 2;
                }
            }
        }

        container a11SessionUpdate {
            tailf:info "A11 Session Update message statistics";
            leaf ReqTotal {
                type decimal64 {
                    fraction-digits 2;
                }
            }
            leaf ReqParseFail {
                type decimal64 {
                    fraction-digits 2;
                }
            }
            leaf AckAccepted {
                type decimal64 {
                    fraction-digits 2;
                }
            }
            leaf AckFailReasonUnspecified {
                type decimal64 {
                    fraction-digits 2;
                }
            }
            leaf AckFailAdminProhibited {
                type decimal64 {
                    fraction-digits 2;
                }
            }
            leaf AckFailAuthFail {
                type decimal64 {
                    fraction-digits 2;
                }
            }
            leaf AckFailIdMismatch {
                type decimal64 {
                    fraction-digits 2;
                }
            }
            leaf AckFailMalformed {
                type decimal64 {
                    fraction-digits 2;
                }
            }
            leaf AckFailOther {
                type decimal64 {
                    fraction-digits 2;
                }
            }
            leaf AckParseFail {
                type decimal64 {
                    fraction-digits 2;
                }
            }
        }

        container a11CapabilitiesInfo {
            tailf:info "A11 Capabilities Info message statistics";
            leaf ReqTotal {
                type decimal64 {
                    fraction-digits 2;
                }
            }
            leaf ReqParseFail {
                type decimal64 {
                    fraction-digits 2;
                }
            }
            leaf AckTotal {
                type decimal64 {
                    fraction-digits 2;
                }
            }
            leaf AckParseFail {
                type decimal64 {
                    fraction-digits 2;
                }
            }
        }

        container other {
            tailf:info "A11 Unparsable message statistics";
            leaf ParseFail {
                type decimal64 {
                    fraction-digits 2;
                }
            }
        }
    }

    typedef MacAddrType {
        type string {
            length 17;
            pattern "([0-9a-fA-F][0-9a-fA-F]:){5}([0-9a-fA-F][0-9a-fA-F])";
        }
    }
}
