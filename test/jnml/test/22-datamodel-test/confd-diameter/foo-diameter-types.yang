submodule foo-diameter-types {
    belongs-to foo-diameter {
        prefix foo-diameter;
    }

    // add new revision statements here

    revision 2011-01-06 {
        description "Conversion from confspec.";
    }


    typedef diameterApplication {
        type bits {
            bit none { position 0; } 
            bit Gy { position 1; } 
            bit Gz { position 2; } 
        }
    }

    typedef diameterWatchdogTimerType {
        type uint16 {
            range "1 .. 300";
        }
    }

    typedef diameterConnectionTimerType {
        type uint16 {
            range "1 .. 300";
        }
    }

    typedef diameterCERTimerType {
        type uint16 {
            range "1 .. 300";
        }
    }

    typedef diameterMaxConnectionAttemptsType {
        type uint32 {
            range "5 .. 4294967295";
        }
    }

    typedef diameterThreadCountType {
        type uint16 {
            range "1 .. 8";
        }
    }

    typedef diameterTransactionPoolSizeType {
        type uint16 {
            range "50 .. 65535";
        }
    }

    typedef diameterMaxUserDataType {
        type uint16 {
            range "128 .. 65535";
        }
    }

    typedef diameterbuffersInPoolType {
        type uint16 {
            range "2048 .. 65535";
        }
    }

    typedef diameterNameType {
        type string {
            length "1 .. 256";
        }
    }
}
