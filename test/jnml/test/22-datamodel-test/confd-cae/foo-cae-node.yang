submodule foo-cae-node {
    belongs-to foo-cae {
        prefix foo-cae;
    }

    import ietf-inet-types {
        prefix inet;
    }

    import tailf-common {
        prefix tailf;
    }

    import foo-system {
        prefix foo-system;
    }

    include foo-cae-types;

    // add new revision statements here

    revision 2011-01-06 {
        description "Conversion from confspec.";
    }


    augment "/foo-system:node" {
        list name {
            key name;
            max-elements 1;
    
            /*  Various identification parameters associated with this node  */
            leaf name {
                type foo-system:nonNullNameType;
                tailf:info "Unique name for this node";
            }
            leaf redundantNodeName {
                type foo-system:nonNullNameType;
                tailf:info "Unique name for the redundancy partner of this node";
            }
        }

        /*  CAE operational mode ATM/Ethernet 3GPP/LTE Monitor/Bypass/Inline etc.,  */
        container operationalMode {
            leaf standard {
                type signalingStandardType;
                default 3gpp;
                tailf:info "Signaling standards to be used";
            }
            leaf service {
                type serviceType;
                default inline;
                tailf:info "Service type to be used";
            }
            leaf opticalBypass {
                type foo-system:enableDisableType;
                default enable;
                tailf:info "Enable optical bypass unit";
            }
            /*  SPX Profile Access  */
            leaf spxProfileAccess {
                type boolean;
                default false;
                tailf:info "Is spx support available for profile access";
            }
        }

        list obs {
            key id;
            config false;
            tailf:cdb-oper;

            leaf id {
                type uint32;
            }
            leaf operStatus {
                type foo-system:adminOperType;
            }
            leaf bypassStatus {
                type bypassStatusType;
            }
            leaf lastSwitchCommand {
                type bypassSwitchCommandsType;
                tailf:info " last command issued ";
            }
            leaf mgmtBypasses {
                type uint32;
            }
            leaf mgmtReversions {
                type uint32;
            }
            leaf sysBypasses {
                type uint32;
            }
            leaf sysReversions {
                type uint32;
            }

            tailf:action command {
                tailf:actionpoint obs;
                tailf:confirm-text "Do you want to proceed?";
                input {
                    leaf type {
                        type bypassSwitchCommandsType;
                        default clear;
                    }
                }
                output {
                    leaf reply {
                        type string;
                    }
                }
            }

            tailf:action debugCommand {
                tailf:actionpoint obsDebug;
                tailf:confirm-text "Do you want to proceed?";
                input {
                    leaf type {
                        type bypassSwitchDebugCommandsType;
                        default forceNoBypass;
                    }
                }
                output {
                    leaf reply {
                        type string;
                    }
                }
            }

            list switch {
                key id;
                tailf:cdb-oper;

                leaf id {
                    type uint32;
                }
                leaf operStatus {
                    type foo-system:adminOperType;
                }
            }

            list powerSupply {
                key id;
                tailf:cdb-oper;

                leaf id {
                    type uint32;
                }
                leaf operStatus {
                    type foo-system:adminOperType;
                }
            }
        }

        container session {
            list ueIp {
                key userIpAddr;
                config false;
                tailf:cdb-oper;

                leaf userIpAddr {
                    type inet:ipv4-address;
                }
                leaf msisdn {
                    type string;
                }
                leaf imsi {
                    type foo-system:imsiType;
                }
                leaf imeisv {
                    type string;
                }
                leaf apn {
                    type string;
                }
                leaf operatorId {
                    type uint32;
                }
                leaf lac {
                    type uint16;
                }
                leaf sac {
                    type uint16;
                }
                leaf mcc {
                    type uint16;
                    tailf:hidden debug;
                }
                leaf mnc {
                    type uint16;
                    tailf:hidden debug;
                }
                leaf tac {
                    type foo-system:tacType;
                }
                leaf Brand {
                    type string;
                }
                leaf Model {
                    type string;
                }
                leaf groupNames {
                    type string;
                }
            }

            list implicitId {
                key Id;
                config false;
                tailf:cdb-oper;

                leaf Id {
                    type uint32;
                }
                leaf userIpAddr {
                    type inet:ipv4-address;
                }
                leaf msisdn {
                    type string;
                }
                leaf imsi {
                    type foo-system:imsiType;
                }
                leaf imeisv {
                    type string;
                }
                leaf apn {
                    type string;
                }
                leaf operatorId {
                    type uint32;
                }
                leaf lac {
                    type uint16;
                }
                leaf sac {
                    type uint16;
                }
                leaf tac {
                    type foo-system:tacType;
                }
                leaf Brand {
                    type string;
                }
                leaf Model {
                    type string;
                }
                leaf groupNames {
                    type string;
                }
            }

            container cumulativeStats {
                config false;
                tailf:cdb-oper;

                leaf attempted {
                    type uint64;
                }
                leaf created {
                    type uint64;
                }
                leaf rejected {
                    type uint64;
                }
                leaf deleted {
                    type uint64;
                }
                leaf createAttemptsByActive {
                    type uint64;
                }
                leaf deleteAttemptsByActive {
                    type uint64;
                }
            }

            container currentStats {
                config false;
                tailf:cdb-oper;

                leaf numActive {
                    type uint64;
                }
                leaf avgSetupTime {
                    type uint64;
                }
                leaf avgHoldTime {
                    type uint64;
                }
            }

            container processingStats {
                config false;
                tailf:hidden debug;
                tailf:cdb-oper;

                leaf numCreateSessionFromRanap {
                    type uint64;
                }
                leaf numDeleteSessionFromRanap {
                    type uint64;
                }
                leaf numResetSessionFromRanap {
                    type uint64;
                }
                leaf numImplicitSessionCreateFromRanap {
                    type uint64;
                }
                leaf numImplicitSessionWithUeIpCreateFromRanap {
                    type uint64;
                }
                leaf numImplicitSessionDeleteFromRanap {
                    type uint64;
                }
                leaf numImplicitSessionWithUeIpDeleteFromRanap {
                    type uint64;
                }
                leaf numQuerySessionToGspm {
                    type uint64;
                }
                leaf numQuerySessionRespFromGspm {
                    type uint64;
                }
                leaf numCreateSessionToGtp {
                    type uint64;
                }
                leaf numCreateSessionRespFromGtp {
                    type uint64;
                }
                leaf numCreateSessionErrorFromGtp {
                    type uint64;
                }
                leaf numDeleteSessionToGtp {
                    type uint64;
                }
                leaf numDeleteSessionRespFromGtp {
                    type uint64;
                }
                leaf numDeleteSessionErrorFromGtp {
                    type uint64;
                }
                leaf numUpdateIndicationFromGspm {
                    type uint64;
                }
                leaf numUpdateIndicationToGtp {
                    type uint64;
                }
            }

            container errorStats {
                config false;
                tailf:hidden debug;
                tailf:cdb-oper;

                leaf numSessionCreateErrorInGtp {
                    type uint64;
                }
                leaf numSessionDeletionErrorInGtp {
                    type uint64;
                }
                leaf numQueryRespErrorFromGspm {
                    type uint64;
                }
            }
        }

        container bearer {
            container stats {
                config false;
                tailf:cdb-oper;

                leaf rxOctets {
                    type uint64;
                }
                leaf txOctets {
                    type uint64;
                }
                leaf discardedOctets {
                    type uint64;
                }
                leaf bypassedPolicyOctets {
                    type uint64;
                }
                leaf bypassedFailureOctets {
                    type uint64;
                }
                leaf rxSouthOctets {
                    type uint64;
                }
                leaf txSouthOctets {
                    type uint64;
                }
                leaf rxNorthOctets {
                    type uint64;
                }
                leaf txNorthOctets {
                    type uint64;
                }
                leaf rxCdsOctets {
                    type uint64;
                }
                leaf txCdsOctets {
                    type uint64;
                }
                leaf rxCdsPkts {
                    type uint64;
                }
                leaf rxCdsPktsTxSouth {
                    type uint64;
                }
                leaf rxCdsPktsTxNorth {
                    type uint64;
                }
                leaf rxCdsPktsDiscarded {
                    type uint64;
                }
                leaf txCdsPkts {
                    type uint64;
                }
            }
        }

        container onlineCharging {
            list sessionUeIp {
                key userIpAddr;
                config false;
                tailf:cdb-oper;

                leaf userIpAddr {
                    type inet:ipv4-address;
                }
                leaf apn {
                    type string;
                }
                leaf chargingImsi {
                    type uint64;
                }
                leaf inputGSU {
                    type int32;
                }
                leaf outputGSU {
                    type int32;
                }
                leaf totalGSU {
                    type int32;
                }
                leaf inputUSU {
                    type int32;
                }
                leaf outputUSU {
                    type int32;
                }
                leaf totalUSU {
                    type int32;
                }
                leaf currentState {
                    type string;
                }
            }

            container stats {
                config false;
                tailf:cdb-oper;

                leaf scmCreateSessionRequests {
                    type uint64;
                }
                leaf interimQuotaRequests {
                    type uint64;
                }
                leaf interimQuotaResponses {
                    type uint64;
                }
                leaf rarRequests {
                    type uint64;
                }
                leaf finalUnitsIndications {
                    type uint64;
                }
            }
        }
    }
}
