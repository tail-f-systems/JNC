submodule foo-cae-atm {
    belongs-to foo-cae {
        prefix foo-cae;
    }

    import ietf-inet-types {
        prefix inet;
    }

    import tailf-common {
        prefix tailf;
    }

    import foo-alarm {
        prefix foo-alarm;
    }

    import foo-system {
        prefix foo-system;
    }

    include foo-cae-types;

    // add new revision statements here

    revision 2011-01-06 {
        description "Conversion from confspec.";
    }


    container atm {
        list saalProfile {
            key name;

            leaf name {
                type foo-system:nameType;
            }
            leaf t1 {
                type saalT1Type;
                default 5000;
                tailf:info '"ms"';
            }
            leaf t2 {
                type saalT2Type;
                default 30000;
                tailf:info '"ms"';
            }
            leaf t3 {
                type saalT3Type;
                default 10;
                tailf:info '"ms"';
            }
            leaf tPoll {
                type saalTPollType;
                default 100;
                tailf:info '"ms"';
            }
            leaf tKeepAlive {
                type saalTKeepAliveType;
                default 100;
                tailf:info '"ms"';
            }
            leaf tIdle {
                type saalTIdleType;
                default 100;
                tailf:info '"ms"';
            }
            leaf tNoResp {
                type saalTNoRespType;
                default 1500;
                tailf:info '"ms"';
            }
            leaf tCc {
                type saalTCcType;
                default 200;
                tailf:info '"ms"';
            }
            leaf n1 {
                type saalN1Type;
                default 1000;
            }
            leaf maxCc {
                type saalMaxCcType;
                default 4;
            }
            leaf maxPd {
                type saalMaxPdType;
                default 500;
            }
            leaf maxStat {
                type saalMaxStatType;
                default 67;
            }
        }

        list controller {
            key "slot subSlot";

            /*  application-specific validation  */

            leaf slot {
                type leafref {
                    path "/foo-system:card/foo-system:slot";
                }
            }
            leaf subSlot {
                type foo-system:subSlotType;
            }
            leaf type {
                type atmControllerType;
                default xs2000;
            }
            leaf clocking {
                type atmClockingType;
                default internal;
            }
            leaf hostDevName {
                type foo-system:nameType;
                mandatory true;
            }
            leaf iwPort {
                type atmIwPortType;
                default 1;
            }
            leaf deviceId {
                type int16;
                default -1;
                tailf:hidden debug;
                tailf:info "optionally override the deviceId for this object";
            }
            leaf simNicIpAddr {
                type inet:ipv4-address;
                default 0.0.0.0;
                tailf:hidden debug;
            }
            leaf simNicMacAddr {
                type foo-system:MacAddrType;
                default 00:00:00:00:00:00;
                tailf:hidden debug;
            }

            container status {
                config false;
                tailf:cdb-oper;

                leaf operStatus {
                    type foo-system:adminOperType;
                }
                leaf macAddr {
                    type foo-system:MacAddrType;
                }
                leaf reason {
                    type string;
                }
            }

            container alarm {
                container atmControllerDown {
                    presence "alarm override";
                    uses foo-alarm:booleanAlarmConfig;
                }
            }
        }

        list port {
            key "slot subSlot port";

            /*  application-specific validation  */

            leaf slot {
                type leafref {
                    path "../../controller/slot";
                }
            }
            leaf subSlot {
                type leafref {
                    path "../../controller/subSlot";
                }
            }
            leaf port {
                type atmPortType;
            }
            leaf framing {
                type atmFramingType;
                default oc3;
            }
            leaf cellScrambling {
                type boolean;
                default true;
            }
            leaf loopback {
                type atmLoopbackType;
                default disabled;
            }
            leaf adminState {
                type foo-system:adminOperType;
                default up;
            }

            container status {
                config false;
                tailf:cdb-oper;

                leaf operStatus {
                    type foo-system:adminOperType;
                }
                leaf alarms {
                    type atmAlarmType;
                }
                leaf reason {
                    type string;
                }
            }

            container sfp {
                config false;
                /*  we use a separate callpoint here since SFP access is slow  */
                /*  this way, 'show atm port counters' will not cause the application to read the SFP  */
                tailf:cdb-oper;

                leaf vendor {
                    type string;
                }
                leaf partNumber {
                    type string;
                }
                leaf revision {
                    type string;
                }
                leaf serialNumber {
                    type string;
                }
                leaf dateCode {
                    type string;
                }
                leaf connector {
                    type string;
                }
                leaf transceiver {
                    type string;
                }
                leaf bitRate {
                    type string;
                }
            }

            container counters {
                config false;
                tailf:cdb-oper;

                leaf rxCells {
                    type uint64;
                }
                leaf rxOamCells {
                    type uint64;
                }
                leaf discardedOamCells {
                    type uint64;
                }
                leaf rxOverflowCells {
                    type uint64;
                }
                leaf rxUnassignedCells {
                    type uint64;
                }
                leaf rxCHECErrors {
                    type uint64;
                }
                leaf rxUHECErrors {
                    type uint64;
                }
                leaf pathBIPErrors {
                    type uint64;
                }
                leaf pathFEBEErrors {
                    type uint64;
                }
                leaf lineBIPErrors {
                    type uint64;
                }
                leaf lineFEBEErrors {
                    type uint64;
                }
                leaf sectionBIPErrors {
                    type uint64;
                }
                leaf rxLastUnassignedVpiVci {
                    type string;
                }
                leaf txCells {
                    type uint64;
                }
                leaf txOamCells {
                    type uint64;
                }
                leaf rxCellRate {
                    type uint32;
                }
                leaf rxUtilization {
                    type uint8;
                }
                leaf txCellRate {
                    type uint32;
                }
                leaf txUtilization {
                    type uint8;
                }
                leaf utilization {
                    type uint8;
                    tailf:hidden true;
                }
            }

            container alarm {
                container atmPortDown {
                    presence "alarm override";
                    uses foo-alarm:booleanAlarmConfig;
                }

                container atmPortUtilizationWarning {
                    presence "alarm override";
                    uses foo-alarm:gaugeAlarmConfig;
                }

                container atmPortUtilization {
                    presence "alarm override";
                    uses foo-alarm:gaugeAlarmConfig;
                }
            }

            /*  oc12/stm4 are allowed only on port 1  */
            must  "((port = 1) or "
                + " ((framing != 'oc12') and (framing != 'stm4')))" {
                tailf:dependency '.';
                error-message "bad framing type";
            }
        }

        /*  endpoint  */
        list endpoint {
            key "slot subSlot port vpi vci";

            leaf slot {
                type leafref {
                    path "../../port/slot";
                }
            }
            leaf subSlot {
                type leafref {
                    path "../../port/subSlot";
                }
            }
            leaf port {
                type leafref {
                    path "../../port/port";
                }
            }
            leaf vpi {
                type atmVpiType;
            }
            leaf vci {
                type atmVciType;
            }

            container ping {
                tailf:action endToEnd {
                    tailf:actionpoint atmPing;
                    input {
                        leaf numAttempts {
                            type uint32;
                            default 5;
                        }
                    }
                    output {
                        leaf status {
                            type string;
                            mandatory true;
                        }
                    }
                }

                tailf:action segment {
                    tailf:actionpoint atmPing;
                    input {
                        leaf numAttempts {
                            type uint32;
                            default 5;
                        }
                    }
                    output {
                        leaf status {
                            type string;
                            mandatory true;
                        }
                    }
                }
            }

            container status {
                config false;
                tailf:cdb-oper;

                leaf pvcType {
                    type pvcTypeType;
                }
                leaf pvcName {
                    type foo-system:nameType;
                }
                leaf operStatus {
                    type foo-system:adminOperType;
                }
                leaf bypass {
                    type boolean;
                }
                leaf udpPort {
                    type inet:port-number;
                    tailf:hidden debug;
                }
                leaf channelId {
                    type int32;
                    tailf:hidden debug;
                }
            }

            container counters {
                config false;
                tailf:cdb-oper;

                leaf rxCells {
                    type uint64;
                    tailf:display-when "../../status/bypass='true'";
                }
                leaf rxOamCells {
                    type uint64;
                }
                leaf discardedOamCells {
                    type uint64;
                }
                leaf rxPkts {
                    type uint64;
                    tailf:display-when "../../status/bypass='false'";
                }
                /*  element is hidden due to lack of support in xalyo driver as of v2.75  */
                leaf rxBytes {
                    type uint64;
                    tailf:hidden full;
                    tailf:display-when "../../status/bypass='false'";
                }
                leaf rxCongestDrops {
                    type uint64;
                    tailf:display-when "../../status/bypass='false'";
                }
                leaf rxOtherDrops {
                    type uint64;
                    tailf:display-when "../../status/bypass='false'";
                }
                leaf txCells {
                    type uint64;
                    tailf:display-when "../../status/bypass='true'";
                }
                leaf txOamCells {
                    type uint64;
                }
                leaf droppedCells {
                    type uint64;
                    tailf:display-when "../../status/bypass='true'";
                }
                leaf txPkts {
                    type uint64;
                    tailf:display-when "../../status/bypass='false'";
                }
                /*  element is hidden due to lack of support in xalyo driver as of v2.75  */
                leaf txBytes {
                    type uint64;
                    tailf:hidden full;
                    tailf:display-when "../../status/bypass='false'";
                }
                leaf txCongestDrops {
                    type uint64;
                    tailf:display-when "../../status/bypass='false'";
                }
                leaf txOtherDrops {
                    type uint64;
                    tailf:display-when "../../status/bypass='false'";
                }
            }

            container pingResult {
                config false;
                tailf:cdb-oper;

                leaf type {
                    type AtmPingType;
                }
                leaf numRemaining {
                    type uint32;
                }
                leaf numSent {
                    type uint32;
                }
                leaf numGood {
                    type uint32;
                }
                leaf numLate {
                    type uint32;
                }
                leaf numMisordered {
                    type uint32;
                }
                leaf avgMillisecs {
                    type uint32;
                }
            }
        }

        container pvc {
            list bearer {
                key name;

                /*  application-specific validation  */

                leaf name {
                    type foo-system:nameType;
                }
                leaf adminState {
                    type foo-system:adminOperType;
                    default up;
                }
                leaf bypass {
                    type boolean;
                    default false;
                }
                leaf mtu {
                    type foo-system:mtuType;
                    default 1500;
                }
                list north {
                    key "slot subSlot port vpi vci";
                    leaf slot {
                        type leafref {
                            path "../../../../endpoint/slot";
                        }
                    }
                    leaf subSlot {
                        type leafref {
                            path "../../../../endpoint/subSlot";
                        }
                    }
                    leaf port {
                        type leafref {
                            path "../../../../endpoint/port";
                        }
                    }
                    leaf vpi {
                        type leafref {
                            path "../../../../endpoint/vpi";
                        }
                    }
                    leaf vci {
                        type leafref {
                            path "../../../../endpoint/vci";
                        }
                    }

                    /* ensure endpoints are different */
                    must  "count(../south[slot=current()/slot][subSlot=current()/subSlot][port=current()/port][vpi=current()/vpi][vci=current()/vci]) = 0" {
                        tailf:dependency '.';
                        tailf:dependency '../south';
                        error-message "north and south endpoints are the same";
                    }
                    
                    /* ensure endpoint not in use by another /atm/pvc/bearer */
                    must "(count(/atm/pvc/bearer/north[slot=current()/slot][subSlot=current()/subSlot][port=current()/port][vpi=current()/vpi][vci=current()/vci]) +"
                        + "count(/atm/pvc/bearer/south[slot=current()/slot][subSlot=current()/subSlot][port=current()/port][vpi=current()/vpi][vci=current()/vci])) <= 1" {
                        tailf:dependency '.';
                        tailf:dependency '../south';
                        error-message "north endpoint in use by a bearer PVC";
                    }

                    /* ensure endpoint not in use by another /atm/pvc/signaling */
                    must "(count(/atm/pvc/signaling/north[slot=current()/slot][subSlot=current()/subSlot][port=current()/port][vpi=current()/vpi][vci=current()/vci]) +"
                        + "count(/atm/pvc/signaling/south[slot=current()/slot][subSlot=current()/subSlot][port=current()/port][vpi=current()/vpi][vci=current()/vci])) <= 1" {
                        tailf:dependency '.';
                        tailf:dependency '/atm/pvc/signaling';
                        error-message "north endpoint in use by a signaling PVC";
                    }

                    /* ensure endpoint not in use by another /atm/pvc/bypass */
                    must "(count(/atm/pvc/bypass/north[slot=current()/slot][subSlot=current()/subSlot][port=current()/port][vpi=current()/vpi][vci=current()/vci]) +"
                        + "count(/atm/pvc/bypass/south[slot=current()/slot][subSlot=current()/subSlot][port=current()/port][vpi=current()/vpi][vci=current()/vci])) <= 1" {
                        tailf:dependency '.';
                        tailf:dependency '/atm/pvc/bypass';
                        error-message "north endpoint in use by a bypass PVC";
                    }
                }

                list south {
                    key "slot subSlot port vpi vci";

                    leaf slot {
                        type leafref {
                            path "../../../../endpoint/slot";
                        }
                    }
                    leaf subSlot {
                        type leafref {
                            path "../../../../endpoint/subSlot";
                        }
                    }
                    leaf port {
                        type leafref {
                            path "../../../../endpoint/port";
                        }
                    }
                    leaf vpi {
                        type leafref {
                            path "../../../../endpoint/vpi";
                        }
                    }
                    leaf vci {
                        type leafref {
                            path "../../../../endpoint/vci";
                        }
                    }

                    /* ensure endpoints are different */
                    must  "count(../north[slot=current()/slot][subSlot=current()/subSlot][port=current()/port][vpi=current()/vpi][vci=current()/vci]) = 0" {
                        tailf:dependency '.';
                        tailf:dependency '../north';
                        error-message "north and south endpoints are the same";
                    }
                    
                    /* ensure endpoint not in use by another /atm/pvc/bearer */
                    must "(count(/atm/pvc/bearer/north[slot=current()/slot][subSlot=current()/subSlot][port=current()/port][vpi=current()/vpi][vci=current()/vci]) +"
                        + "count(/atm/pvc/bearer/south[slot=current()/slot][subSlot=current()/subSlot][port=current()/port][vpi=current()/vpi][vci=current()/vci])) <= 1" {
                        tailf:dependency '.';
                        tailf:dependency '../south';
                        error-message "north endpoint in use by a bearer PVC";
                    }

                    /* ensure endpoint not in use by another /atm/pvc/signaling */
                    must "(count(/atm/pvc/signaling/north[slot=current()/slot][subSlot=current()/subSlot][port=current()/port][vpi=current()/vpi][vci=current()/vci]) +"
                        + "count(/atm/pvc/signaling/south[slot=current()/slot][subSlot=current()/subSlot][port=current()/port][vpi=current()/vpi][vci=current()/vci])) <= 1" {
                        tailf:dependency '.';
                        tailf:dependency '/atm/pvc/signaling';
                        error-message "north endpoint in use by a signaling PVC";
                    }

                    /* ensure endpoint not in use by another /atm/pvc/bypass */
                    must "(count(/atm/pvc/bypass/north[slot=current()/slot][subSlot=current()/subSlot][port=current()/port][vpi=current()/vpi][vci=current()/vci]) +"
                        + "count(/atm/pvc/bypass/south[slot=current()/slot][subSlot=current()/subSlot][port=current()/port][vpi=current()/vpi][vci=current()/vci])) <= 1" {
                        tailf:dependency '.';
                        tailf:dependency '/atm/pvc/bypass';
                        error-message "north endpoint in use by a bypass PVC";
                    }
                }

                container status {
                    config false;
                    tailf:cdb-oper;

                    leaf operStatus {
                        type foo-system:adminOperType;
                    }
                }
            }

            list signaling {
                key name;

                /*  application-specific validation  */

                leaf name {
                    type foo-system:nameType;
                }
                leaf adminState {
                    type foo-system:adminOperType;
                    default up;
                }
                leaf bypass {
                    type boolean;
                    default false;
                }

                list north {
                    key "slot subSlot port vpi vci";
                    leaf slot {
                        type leafref {
                            path "../../../../endpoint/slot";
                        }
                    }
                    leaf subSlot {
                        type leafref {
                            path "../../../../endpoint/subSlot";
                        }
                    }
                    leaf port {
                        type leafref {
                            path "../../../../endpoint/port";
                        }
                    }
                    leaf vpi {
                        type leafref {
                            path "../../../../endpoint/vpi";
                        }
                    }
                    leaf vci {
                        type leafref {
                            path "../../../../endpoint/vci";
                        }
                    }

                    /* ensure endpoints are different */
                    must  "count(../south[slot=current()/slot][subSlot=current()/subSlot][port=current()/port][vpi=current()/vpi][vci=current()/vci]) = 0" {
                        tailf:dependency '.';
                        tailf:dependency '../south';
                        error-message "north and south endpoints are the same";
                    }
                    
                    /* ensure endpoint not in use by another /atm/pvc/signaling */
                    must "(count(/atm/pvc/signaling/north[slot=current()/slot][subSlot=current()/subSlot][port=current()/port][vpi=current()/vpi][vci=current()/vci]) +"
                        + "count(/atm/pvc/signaling/south[slot=current()/slot][subSlot=current()/subSlot][port=current()/port][vpi=current()/vpi][vci=current()/vci])) <= 1" {
                        tailf:dependency '.';
                        tailf:dependency '../south';
                        error-message "north endpoint in use by a signaling PVC";
                    }

                    /* ensure endpoint not in use by another /atm/pvc/bearer */
                    must "(count(/atm/pvc/bearer/north[slot=current()/slot][subSlot=current()/subSlot][port=current()/port][vpi=current()/vpi][vci=current()/vci]) +"
                        + "count(/atm/pvc/bearer/south[slot=current()/slot][subSlot=current()/subSlot][port=current()/port][vpi=current()/vpi][vci=current()/vci])) <= 1" {
                        tailf:dependency '.';
                        tailf:dependency '/atm/pvc/bearer';
                        error-message "north endpoint in use by a bearer PVC";
                    }

                    /* ensure endpoint not in use by another /atm/pvc/bypass */
                    must "(count(/atm/pvc/bypass/north[slot=current()/slot][subSlot=current()/subSlot][port=current()/port][vpi=current()/vpi][vci=current()/vci]) +"
                        + "count(/atm/pvc/bypass/south[slot=current()/slot][subSlot=current()/subSlot][port=current()/port][vpi=current()/vpi][vci=current()/vci])) <= 1" {
                        tailf:dependency '.';
                        tailf:dependency '/atm/pvc/bypass';
                        error-message "north endpoint in use by a bypass PVC";
                    }
                }

                list south {
                    key "slot subSlot port vpi vci";

                    leaf slot {
                        type leafref {
                            path "../../../../endpoint/slot";
                        }
                    }
                    leaf subSlot {
                        type leafref {
                            path "../../../../endpoint/subSlot";
                        }
                    }
                    leaf port {
                        type leafref {
                            path "../../../../endpoint/port";
                        }
                    }
                    leaf vpi {
                        type leafref {
                            path "../../../../endpoint/vpi";
                        }
                    }
                    leaf vci {
                        type leafref {
                            path "../../../../endpoint/vci";
                        }
                    }

                    /* ensure endpoints are different */
                    must  "count(../north[slot=current()/slot][subSlot=current()/subSlot][port=current()/port][vpi=current()/vpi][vci=current()/vci]) = 0" {
                        tailf:dependency '.';
                        tailf:dependency '../north';
                        error-message "north and south endpoints are the same";
                    }
                    
                    /* ensure endpoint not in use by another /atm/pvc/signaling */
                    must "(count(/atm/pvc/signaling/north[slot=current()/slot][subSlot=current()/subSlot][port=current()/port][vpi=current()/vpi][vci=current()/vci]) +"
                        + "count(/atm/pvc/signaling/south[slot=current()/slot][subSlot=current()/subSlot][port=current()/port][vpi=current()/vpi][vci=current()/vci])) <= 1" {
                        tailf:dependency '.';
                        tailf:dependency '../south';
                        error-message "north endpoint in use by a signaling PVC";
                    }

                    /* ensure endpoint not in use by another /atm/pvc/bearer */
                    must "(count(/atm/pvc/bearer/north[slot=current()/slot][subSlot=current()/subSlot][port=current()/port][vpi=current()/vpi][vci=current()/vci]) +"
                        + "count(/atm/pvc/bearer/south[slot=current()/slot][subSlot=current()/subSlot][port=current()/port][vpi=current()/vpi][vci=current()/vci])) <= 1" {
                        tailf:dependency '.';
                        tailf:dependency '/atm/pvc/bearer';
                        error-message "north endpoint in use by a bearer PVC";
                    }

                    /* ensure endpoint not in use by another /atm/pvc/bypass */
                    must "(count(/atm/pvc/bypass/north[slot=current()/slot][subSlot=current()/subSlot][port=current()/port][vpi=current()/vpi][vci=current()/vci]) +"
                        + "count(/atm/pvc/bypass/south[slot=current()/slot][subSlot=current()/subSlot][port=current()/port][vpi=current()/vpi][vci=current()/vci])) <= 1" {
                        tailf:dependency '.';
                        tailf:dependency '/atm/pvc/bypass';
                        error-message "north endpoint in use by a bypass PVC";
                    }
                }

                container status {
                    config false;
                    tailf:cdb-oper;

                    leaf operStatus {
                        type foo-system:adminOperType;
                    }
                }
            }

            list bypass {
                key name;

                /*  application-specific validation  */

                leaf name {
                    type foo-system:nameType;
                }
                leaf adminState {
                    type foo-system:adminOperType;
                    default up;
                }
                list north {
                    key "slot subSlot port vpi vci";
                    leaf slot {
                        type leafref {
                            path "../../../../endpoint/slot";
                        }
                    }
                    leaf subSlot {
                        type leafref {
                            path "../../../../endpoint/subSlot";
                        }
                    }
                    leaf port {
                        type leafref {
                            path "../../../../endpoint/port";
                        }
                    }
                    leaf vpi {
                        type leafref {
                            path "../../../../endpoint/vpi";
                        }
                    }
                    leaf vci {
                        type leafref {
                            path "../../../../endpoint/vci";
                        }
                    }

                    /* ensure endpoints are different */
                    must  "count(../south[slot=current()/slot][subSlot=current()/subSlot][port=current()/port][vpi=current()/vpi][vci=current()/vci]) = 0" {
                        tailf:dependency '.';
                        tailf:dependency '../south';
                        error-message "north and south endpoints are the same";
                    }
                    
                    /* ensure endpoint not in use by another /atm/pvc/bypass */
                    must "(count(/atm/pvc/bypass/north[slot=current()/slot][subSlot=current()/subSlot][port=current()/port][vpi=current()/vpi][vci=current()/vci]) +"
                        + "count(/atm/pvc/bypass/south[slot=current()/slot][subSlot=current()/subSlot][port=current()/port][vpi=current()/vpi][vci=current()/vci])) <= 1" {
                        tailf:dependency '.';
                        tailf:dependency '../south';
                        error-message "north endpoint in use by a bypass PVC";
                    }

                    /* ensure endpoint not in use by another /atm/pvc/signaling */
                    must "(count(/atm/pvc/signaling/north[slot=current()/slot][subSlot=current()/subSlot][port=current()/port][vpi=current()/vpi][vci=current()/vci]) +"
                        + "count(/atm/pvc/signaling/south[slot=current()/slot][subSlot=current()/subSlot][port=current()/port][vpi=current()/vpi][vci=current()/vci])) <= 1" {
                        tailf:dependency '.';
                        tailf:dependency '/atm/pvc/signaling';
                        error-message "north endpoint in use by a signaling PVC";
                    }

                    /* ensure endpoint not in use by another /atm/pvc/bearer */
                    must "(count(/atm/pvc/bearer/north[slot=current()/slot][subSlot=current()/subSlot][port=current()/port][vpi=current()/vpi][vci=current()/vci]) +"
                        + "count(/atm/pvc/bearer/south[slot=current()/slot][subSlot=current()/subSlot][port=current()/port][vpi=current()/vpi][vci=current()/vci])) <= 1" {
                        tailf:dependency '.';
                        tailf:dependency '/atm/pvc/bearer';
                        error-message "north endpoint in use by a bearer PVC";
                    }
                }

                list south {
                    key "slot subSlot port vpi vci";

                    leaf slot {
                        type leafref {
                            path "../../../../endpoint/slot";
                        }
                    }
                    leaf subSlot {
                        type leafref {
                            path "../../../../endpoint/subSlot";
                        }
                    }
                    leaf port {
                        type leafref {
                            path "../../../../endpoint/port";
                        }
                    }
                    leaf vpi {
                        type leafref {
                            path "../../../../endpoint/vpi";
                        }
                    }
                    leaf vci {
                        type leafref {
                            path "../../../../endpoint/vci";
                        }
                    }

                    /* ensure endpoints are different */
                    must  "count(../north[slot=current()/slot][subSlot=current()/subSlot][port=current()/port][vpi=current()/vpi][vci=current()/vci]) = 0" {
                        tailf:dependency '.';
                        tailf:dependency '../north';
                        error-message "north and south endpoints are the same";
                    }
                    
                    /* ensure endpoint not in use by another /atm/pvc/bypass */
                    must "(count(/atm/pvc/bypass/north[slot=current()/slot][subSlot=current()/subSlot][port=current()/port][vpi=current()/vpi][vci=current()/vci]) +"
                        + "count(/atm/pvc/bypass/south[slot=current()/slot][subSlot=current()/subSlot][port=current()/port][vpi=current()/vpi][vci=current()/vci])) <= 1" {
                        tailf:dependency '.';
                        tailf:dependency '../south';
                        error-message "north endpoint in use by a bypass PVC";
                    }

                    /* ensure endpoint not in use by another /atm/pvc/signaling */
                    must "(count(/atm/pvc/signaling/north[slot=current()/slot][subSlot=current()/subSlot][port=current()/port][vpi=current()/vpi][vci=current()/vci]) +"
                        + "count(/atm/pvc/signaling/south[slot=current()/slot][subSlot=current()/subSlot][port=current()/port][vpi=current()/vpi][vci=current()/vci])) <= 1" {
                        tailf:dependency '.';
                        tailf:dependency '/atm/pvc/signaling';
                        error-message "north endpoint in use by a signaling PVC";
                    }

                    /* ensure endpoint not in use by another /atm/pvc/bearer */
                    must "(count(/atm/pvc/bearer/north[slot=current()/slot][subSlot=current()/subSlot][port=current()/port][vpi=current()/vpi][vci=current()/vci]) +"
                        + "count(/atm/pvc/bearer/south[slot=current()/slot][subSlot=current()/subSlot][port=current()/port][vpi=current()/vpi][vci=current()/vci])) <= 1" {
                        tailf:dependency '.';
                        tailf:dependency '/atm/pvc/bearer';
                        error-message "north endpoint in use by a bearer PVC";
                    }
                }

                container status {
                    config false;
                    tailf:cdb-oper;

                    leaf operStatus {
                        type foo-system:adminOperType;
                        mandatory true;
                    }
                }
            }
        }
    }
}
