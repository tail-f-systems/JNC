submodule foo-cae-simulator {
    belongs-to foo-cae {
        prefix foo-cae;
    }

    import ietf-inet-types {
        prefix inet;
    }

    import tailf-common {
        prefix tailf;
    }

    import foo-system {
        prefix foo-system;
    }

    include foo-cae-types;
    include foo-cae-atm;

    // add new revision statements here

    revision 2011-01-06 {
        description "Conversion from confspec.";
    }


    container simulator {
        tailf:hidden simulator;

        list node {
            key name;
            max-elements 1;

            leaf name {
                type foo-system:nameType;
                tailf:info "% Arbitrary name to identify the node";
            }
            leaf rnc {
                type inet:ipv4-address;
                default 0.0.0.0;
                tailf:info "% IP address of the RNC";
            }
            leaf sgsn {
                type inet:ipv4-address;
                default 0.0.0.0;
                tailf:info "% IP address of the SGSN";
            }
            leaf dns {
                type inet:ipv4-address;
                default 0.0.0.0;
                tailf:info "% IP address of the primary DNS";
            }
            leaf dns-secondary {
                type inet:ipv4-address;
                default 0.0.0.0;
                tailf:info "% IP address of the secondary DNS";
            }
            leaf tracing {
                type boolean;
                default false;
                tailf:info "% Enables tracing for all simulator processes %";
            }

            container signaling {
                tailf:info "% Signaling related configuration";

                container flags {
                    leaf identity-request {
                        type boolean;
                        default false;
                        tailf:info "% Enables GMM Identity Request procedure from CNSIM %";
                    }
                    leaf auth-and-cyphering-request {
                        type boolean;
                        default false;
                        tailf:info "% Enables GMM Auth and Cyphering Request procedure from CNSIM %";
                    }
                    leaf link-selection {
                        type boolean;
                        default false;
                        tailf:info "% If signalling link selection requested %";
                    }
                    leaf sctp-ip-filter {
                        type boolean;
                        default false;
                        tailf:info "% Filter msg based on sctp end point configuration %";
                    }
                }

                container params {
                    leaf src-mac {
                        type foo-system:MacAddrType;
                        default 00:00:00:00:00:00;
                        tailf:info "% Source MAC address to be used for SCTP packets %";
                    }
                    leaf dest-mac {
                        type foo-system:MacAddrType;
                        default ff:ff:ff:ff:ff:ff;
                        tailf:info "% Destination MAC address to be used for SCTP packets %";
                    }
                    leaf vlan {
                        type uint16;
                        default 0;
                        tailf:info "% VLAN tag to be used for SCTP packets %";
                    }
                    leaf dscp {
                        type uint8;
                        default 0;
                        tailf:info "% TOS/DSCP byte to be used for SCTP packets %";
                    }

                }
                list linksel {
                    key id;

                    leaf id {
                        type uint32;
                    }
                    leaf startId {
                        type uint32;
                        mandatory true;
                        tailf:info "% Start Link Selection Id %";
                    }
                    leaf endId {
                        type uint32;
                        mandatory true;
                        tailf:info "% End Link Selection Id %";
                    }
                    leaf pvcName {
                        type leafref {
                            path "/atm/pvc/signaling/name";
                        }
                        mandatory true;
                        tailf:info "% Pvc name for range of Ids %";
                    }
                }
            }

            container bearer {
                tailf:info "% Bearer related configuration";

                container gtp {
                    leaf srcPort {
                        type uint16;
                        default 2152;
                        tailf:info "% Source port used in GTP packets %";
                    }
                    leaf dstPort {
                        type uint16;
                        default 2152;
                        tailf:info "% Destination port used in GTP packets %";
                    }
                    leaf sequenceNumbers {
                        type boolean;
                        default false;
                        tailf:info "% Use sequence numbers in GTP packets %";
                    }
                    leaf inflightPacketDelay {
                        type uint16;
                        default 0;
                        tailf:info "% Allow GTP packets to flow for the specified seconds after tunnel is deleted from control plane (65535 for infinite)%";
                    }
                }

                container message-burst {
                    leaf size {
                        type uint32;
                        default 200;
                        tailf:info "% Maximum number of UEs to be sent from dp to uesim %";
                    }
                    leaf interval {
                        type uint32;
                        default 1;
                        tailf:info "% Time interval between successive messages from dp to ue sim %";
                    }
                }

                container flag {
                    leaf reestablish-on-link-failure {
                        type boolean;
                        default false;
                        tailf:info "% whether to reestablish the connection on link failure";
                    }
                }

                leaf link-selection {
                    type boolean;
                    default false;
                    tailf:info "% If bearer link selection requested";
                }

                list linksel {
                    key id;

                    leaf id {
                        type uint32;
                    }
                    leaf startId {
                        type uint32;
                        mandatory true;
                        tailf:info "% Start Link Selection Id %";
                    }
                    leaf endId {
                        type uint32;
                        mandatory true;
                        tailf:info "% End Link Selection Id %";
                    }
                    leaf pvcName {
                        type leafref {
                            path "/atm/pvc/bearer/name";
                        }
                        mandatory true;
                        tailf:info "% Pvc name for range of Ids %";
                    }
                }
            }
        }

        list transport {
            key interface;

            leaf interface {
                type string;
            }
            leaf src-mac {
                type foo-system:MacAddrType;
                mandatory true;
            }
            leaf dest-mac {
                type foo-system:MacAddrType;
                mandatory true;
            }
            leaf mtu {
                type simMtu;
                default 1500;
            }
            leaf cfm-health-check-enabled {
                type boolean;
                default false;
            }
            leaf icmp-health-check-enabled {
                type boolean;
                default false;
            }
            leaf src-mac-validation-enabled {
                type boolean;
                default false;
            }
            leaf dst-mac-validation-enabled {
                type boolean;
                default false;
            }

            container transportStats {
                config false;
                tailf:cdb-oper;

                leaf packets-with-bad-dest-mac {
                    type uint64;
                }
                leaf packets-with-bad-source-mac {
                    type uint64;
                }
            }
        }

        list subnetpool {
            key name;

            leaf name {
                type foo-system:nameType;
            }
            leaf ip {
                type inet:ipv4-address;
                mandatory true;
            }
            leaf mask {
                type inet:ipv4-address;
                default 255.255.255.0;
            }
            leaf vlantag {
                type uint16;
                default 0;
            }
            leaf mtu {
                type simMtu;
                default 1460;
            }
            leaf local {
                type boolean;
                default false;
            }
            leaf dscp {
                type uint8;
                default 0;
            }
        }
    }
}
