module types {
    namespace "http://tail-f.com/ns/types";
    prefix types;
    
    import ietf-inet-types {
        prefix inet;
    }

    import ietf-yang-types {
        prefix yang;
    }

    container types {
        container builtin {
            leaf binary { type binary; }
            leaf boolean { type boolean; }
            leaf empty { type empty; }
            leaf enumeration {
                type enumeration {
                    enum foo;
                    enum bar;
                }
            }
            leaf uint8 { type uint8; }
            leaf uint16 { type uint16; }
            leaf uint32 { type uint32; }
            leaf uint64 { type uint64; }
            leaf int8 { type int8; }
            leaf int16 { type int16; }
            leaf int32 { type int32; }
            leaf int64 { type int64; }
            leaf string { type string; }
        }
        
        container yang-types {
            leaf counter32 { type yang:counter32; }
            leaf zero-based-counter32 { type yang:zero-based-counter32; }
            leaf counter64 { type yang:counter64; }
            leaf zero-based-counter64 { type yang:zero-based-counter64; }
            leaf gauge32 { type yang:gauge32; }
            leaf gauge64 { type yang:gauge64; }
            leaf date-and-time { type yang:date-and-time; }
            leaf timeticks { type yang:timeticks; }
            leaf timestamp { type yang:timestamp; }
            leaf phys-address { type yang:phys-address; }
            leaf mac-address { type yang:mac-address; }
            leaf xpath10 { type yang:xpath1.0; }
        }
        
        container inet-types {
            leaf ip-version { type inet:ip-version; }
            leaf dscp { type inet:dscp; }
            leaf ipv6-flow-label { type inet:ipv6-flow-label; }
            leaf port-number { type inet:port-number; }
            leaf as-number { type inet:as-number; }
            leaf ip-address { type inet:ip-address; }
            leaf ipv4-address { type inet:ipv4-address; }
            leaf ipv6-address { type inet:ipv6-address; }
            leaf ip-prefix { type inet:ip-prefix; }
            leaf ipv4-prefix { type inet:ipv4-prefix; }
            leaf ipv6-prefix { type inet:ipv6-prefix; }
            leaf domain-name { type inet:domain-name; }
            leaf host { type inet:host; }
            leaf uri { type inet:uri; }        
        }

        typedef localType {
            type uint32 {
                range 0..200;
            }
        }
        
        container inline-types {
            container servers {
                container servers {
                    list server {
                        key "foo";
                        leaf foo {
                            type string {
                                pattern "aabb";
                            }
                        }
                        leaf bar {
                            type localType {
                                range 0..100;
                            }
                        }
                    }
                }
            }
            leaf foo {
                type string {
                    pattern "aabb";
                }
            }
            leaf bar {
                type localType {
                    range 0..100;
                }
            }
        }
    }
}
