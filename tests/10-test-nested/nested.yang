module union {
  namespace "http://acme.com/ns/nested/1.0";
  prefix nested;
  list nested {
    key k;
    leaf k {
      type string;
    }
    container nested {
      leaf l {
        type string;
      }
    }
  }
}
