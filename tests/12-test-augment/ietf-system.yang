module ietf-system {
  namespace "urn:ietf:params:xml:ns:yang:ietf-system";
  prefix sys;

  import ietf-inet-types {
    prefix inet;
  }

  container system {
    container ntp {
      list ntp-server {
        key "address";
        leaf address {
          type inet:ip-address;
        }
      }
    }
  }
}
