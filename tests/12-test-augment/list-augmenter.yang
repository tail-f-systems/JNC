module list-augmenter {
    namespace "http://domain.com/ns/test";
    prefix test;
    
    import ietf-system {
      prefix ietf-sys;
    }
    import ietf-inet-types {
      prefix inet;
    }

    augment "/ietf-sys:system/ietf-sys:ntp" {
         /*
          * Alternate (simpler) NTP model.  This replaces the standard one in
          * the ietf model and follows the same style as the DNS servers.
          */
         list server {
            key address;
            
            leaf address {
                type inet:ip-address;
                description
                   "Addresses of the NTP servers to use for system clock
                    synchronization.

                    Implementations MAY limit the number of entries in this
                    leaf list.";
            }
         }
    }
}
