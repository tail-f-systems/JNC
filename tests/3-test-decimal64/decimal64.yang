module decimal64 {
  namespace "http://acme.com/ns/decimal64/1.0";
  prefix decimal64;
  typedef decimal64-2 {
    type decimal64 {
      fraction-digits 2;
    }
  }
  container c {
    container c2;
    container c3;
    leaf decimal64-leaf {
      type decimal64-2;
    }
    list l {
      key "key1 key2";
      leaf key1 {
        type string;
      }
      leaf key2 {
        type decimal64 {
          fraction-digits 4;
        }
      }
      leaf thirty-seven {
        type decimal64 {
          fraction-digits 3;
        }
        default 37.0;
      }
      container c2;
    }
  }
}
