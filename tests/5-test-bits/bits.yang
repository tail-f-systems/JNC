module bits {
  namespace "http://acme.com/ns/bits/1.0";
  prefix bits;
  typedef bits-2 {
    type bits {
      bit a; // position 0
      bit c {
        position 2;
      }
      bit d; // position 3
    }
  }
  container c {
    leaf bits-leaf {
      type bits {
        bit b1 {
          position 1;
        }
        bit b2; // position 2;
        bit b4 {
          position 4;
        }
      }
      default "b1 b2";
    }
    leaf-list llist {
      type bits-2;
    }
    list l {
      key "key1 key2";
      leaf key1 {
        type bits-2;
      }
      leaf key2 {
        type bits {
          bit vital;
          bit warning;
          bit error;
          bit wait;
          bit ready;
        }
      }
      leaf ac {
        type bits-2;
        default "a c";
      }
      leaf-list l-settings {
        type bits {
          bit set-enable {
            position 2;
          }
          bit activate {
            position 4;
          }
          bit forward {
            position 8;
          }
          bit timeout {
            position 16;
          }
        }
      }
    }
  }
}
