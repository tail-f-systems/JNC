module enumeration {
  namespace "http://acme.com/ns/enumeration/1.0";
  prefix enumeration;
  typedef enumeration1 {
    type enumeration {
      enum 0;
      enum one;
      enum two;
      enum 37;
    }
  }
  container c {
    container c2;
    container c3;
    leaf enumeration-leaf {
      type enumeration1;
    }
    list l {
      key "key1 key2";
      leaf key1 {
        type string;
      }
      leaf key2 {
        type enumeration {
          enum xxx;
          enum abc;
          enum 7;
          enum 0;
        }
      }
      leaf thirty-seven {
        type enumeration1;
        default 37;
      }
      container c2;
    }
  }
}
