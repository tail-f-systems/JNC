module augment-test {

  namespace "http://test.com/ns/aug/1.0";
  prefix aug;
  
  import augmentee {
  	prefix "augee";
  }

  organization
   "Tail-f Systems AB";

  contact
   "Emil Wall <mailto:emil@tail-f.com>";

  description 
   "Augments /augee:target (of module augmentee), with a container";

  augment "/augee:target" {
    container augmented {
      leaf data {
        type string;
      }
    }
  }

}
