module augment-self {

  namespace "http://test.com/ns/augself/1.0";
  prefix augself;

  organization
   "Tail-f Systems AB";

  contact
   "Emil Wall <mailto:emil@tail-f.com>";

  description
   "Augments target with data";

  container target {
    leaf d {
      type int32;
    }
  }

  augment "/augself:target" {
    leaf data {
      type string;
    }
  }

}
