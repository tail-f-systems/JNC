module typedef-test {

  namespace "http://test.com/ns/typedef/1.0";
  prefix typedef;

  organization
   "Tail-f Systems AB";

  contact
   "Emil Wall <mailto:emil@tail-f.com>";

  description 
   "Contains definitions of derived types.";

  typedef mytype {
    type string;
  }

  container c {
    leaf m {
      type mytype;
    }
  }

}
